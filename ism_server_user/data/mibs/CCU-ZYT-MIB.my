--
-- CCU-ZYT-MIB.my
-- MIB generated by MG-SOFT Visual MIB Builder Version 6.0  Build 88
-- Tuesday, March 05, 2019 at 11:19:34
--

--  CCU-ZYT-MIB.my
-- MIB generated by MG-SOFT Visual MIB Builder Version 6.0  Build 88
-- Saturday, January 26, 2019 at 18:06:21
-- 

	CCU-ZYT-MIB DEFINITIONS ::= BEGIN
 
		IMPORTS
			enterprises, Integer32, OBJECT-TYPE, MODULE-IDENTITY			
				FROM SNMPv2-SMI;
	
	
--  1.3.6.1.4.1.2011
-- January 24, 2019 at 09:55 GMT
		-- 1.3.6.1.4.1.2011
		huawei MODULE-IDENTITY 
			LAST-UPDATED "201901240955Z"		-- January 24, 2019 at 09:55 GMT
			ORGANIZATION 
				"Organization."
			CONTACT-INFO 
				"Contact-info."
			DESCRIPTION 
				"Description."
			::= { enterprises 2011 }

		
	
--
-- Node definitions
--
	
--  Node definitions
-- 
-- 1.3.6.1.4.1.2011.2
		-- 1.3.6.1.4.1.2011.2
		products OBJECT IDENTIFIER ::= { huawei 2 }

		
--  1.3.6.1.4.1.2011.2.217
		-- 1.3.6.1.4.1.2011.2.217
		hwiSMP OBJECT IDENTIFIER ::= { products 217 }

		
--  1.3.6.1.4.1.2011.2.217.7
		-- 1.3.6.1.4.1.2011.2.217.7
		hwLcs OBJECT IDENTIFIER ::= { hwiSMP 7 }

		
--  1.3.6.1.4.1.2011.2.217.7.1
		-- 1.3.6.1.4.1.2011.2.217.7.1
		hwSystem OBJECT IDENTIFIER ::= { hwLcs 1 }

		
--  1.3.6.1.4.1.2011.2.217.7.1.1
		-- 1.3.6.1.4.1.2011.2.217.7.1.1
		systemParameter OBJECT IDENTIFIER ::= { hwSystem 1 }

		
--  1.3.6.1.4.1.2011.2.217.7.1.1.1
		-- 1.3.6.1.4.1.2011.2.217.7.1.1.1
		softwareVersion OBJECT-TYPE
			SYNTAX Integer32
			MAX-ACCESS read-only
			STATUS current
			DESCRIPTION
				"Description."
			::= { systemParameter 1 }

		
--  1.3.6.1.4.1.2011.2.217.7.1.1.2
		-- 1.3.6.1.4.1.2011.2.217.7.1.1.2
		hardwareVersion OBJECT-TYPE
			SYNTAX OCTET STRING
			MAX-ACCESS read-only
			STATUS current
			DESCRIPTION
				"Description."
			::= { systemParameter 2 }      

--  1.3.6.1.4.1.2011.2.217.7.1.1.3
		-- 1.3.6.1.4.1.2011.2.217.7.1.1.3
		systemModuleName OBJECT-TYPE
			SYNTAX OCTET STRING
			MAX-ACCESS read-only
			STATUS current
			DESCRIPTION
				"Description."
			::= { systemParameter 3 }
			
			
--  1.3.6.1.4.1.2011.2.217.7.1.1.4
		-- 1.3.6.1.4.1.2011.2.217.7.1.1.4
		ccuNetworkParams OBJECT-TYPE
			SYNTAX OCTET STRING
			MAX-ACCESS read-write
			STATUS current
			DESCRIPTION
				"Description."
			::= { systemParameter 4 }		

--  1.3.6.1.4.1.2011.2.217.7.1.1.7
		-- 1.3.6.1.4.1.2011.2.217.7.1.1.7
		ccuMAC OBJECT-TYPE
			SYNTAX OCTET STRING
			MAX-ACCESS read-write
			STATUS current
			DESCRIPTION
				"Description."
			::= { systemParameter 7 }				

		
--  1.3.6.1.4.1.2011.2.217.7.1.1.8
		-- 1.3.6.1.4.1.2011.2.217.7.1.1.8
		reStrat OBJECT-TYPE
			SYNTAX Integer32
			MAX-ACCESS read-write
			STATUS current
			DESCRIPTION
				"Description."
			::= { systemParameter 8 }

		
--  1.3.6.1.4.1.2011.2.217.7.1.1.9
		-- 1.3.6.1.4.1.2011.2.217.7.1.1.9
		time OBJECT-TYPE
			SYNTAX OCTET STRING
			MAX-ACCESS read-write
			STATUS current
			DESCRIPTION
				"Description."
			::= { systemParameter 9 }

		
--  1.3.6.1.4.1.2011.2.217.7.1.1.12
		-- 1.3.6.1.4.1.2011.2.217.7.1.1.12
		encryptionAuthenticationMode OBJECT-TYPE
			SYNTAX Integer32
			MAX-ACCESS read-only
			STATUS current
			DESCRIPTION
				"Description."
			::= { systemParameter 12 }

		
--  1.3.6.1.4.1.2011.2.217.7.1.1.13
		-- 1.3.6.1.4.1.2011.2.217.7.1.1.13
		encryptionAuthenticationKey OBJECT-TYPE
			SYNTAX OCTET STRING
			MAX-ACCESS write-only
			STATUS current
			DESCRIPTION
				"Description."
			::= { systemParameter 13 }
			
--  1.3.6.1.4.1.2011.2.217.7.1.1.16
		-- 1.3.6.1.4.1.2011.2.217.7.1.1.16
		snmpAgentPort OBJECT-TYPE
			SYNTAX Integer32
			MAX-ACCESS read-only
			STATUS current
			DESCRIPTION
				"default 161"
			::= { systemParameter 16 }
			
--  1.3.6.1.4.1.2011.2.217.7.1.1.17
		-- 1.3.6.1.4.1.2011.2.217.7.1.1.17
		trap1SecurityParams OBJECT-TYPE
			SYNTAX OCTET STRING
			MAX-ACCESS write-only
			STATUS current
			DESCRIPTION
				""
			::= { systemParameter 17 }
			
--  1.3.6.1.4.1.2011.2.217.7.1.1.18
		-- 1.3.6.1.4.1.2011.2.217.7.1.1.18
		trap2SecurityParams OBJECT-TYPE
			SYNTAX OCTET STRING
			MAX-ACCESS write-only
			STATUS current
			DESCRIPTION
				""
			::= { systemParameter 18 }	
			
--  1.3.6.1.4.1.2011.2.217.7.1.1.19
		-- 1.3.6.1.4.1.2011.2.217.7.1.1.19
		trap3SecurityParams OBJECT-TYPE
			SYNTAX OCTET STRING
			MAX-ACCESS write-only
			STATUS current
			DESCRIPTION
				""
			::= { systemParameter 19 }				
		
--  1.3.6.1.4.1.2011.2.217.7.1.2
		-- 1.3.6.1.4.1.2011.2.217.7.1.2
		ftp OBJECT IDENTIFIER ::= { hwSystem 2 }

		
--  1.3.6.1.4.1.2011.2.217.7.1.2.1
		-- 1.3.6.1.4.1.2011.2.217.7.1.2.1
		fileName OBJECT-TYPE
			SYNTAX OCTET STRING
			MAX-ACCESS read-write
			STATUS current
			DESCRIPTION
				"Description."
			::= { ftp 1 }

		
--  1.3.6.1.4.1.2011.2.217.7.1.2.2
		-- 1.3.6.1.4.1.2011.2.217.7.1.2.2
		sftpName OBJECT-TYPE
			SYNTAX OCTET STRING
			MAX-ACCESS write-only
			STATUS current
			DESCRIPTION
				"Description."
			::= { ftp 2 }

		
--  1.3.6.1.4.1.2011.2.217.7.1.2.3
		-- 1.3.6.1.4.1.2011.2.217.7.1.2.3
		sftpKey OBJECT-TYPE
			SYNTAX OCTET STRING
			MAX-ACCESS write-only
			STATUS current
			DESCRIPTION
				"Description."
			::= { ftp 3 }
--  1.3.6.1.4.1.2011.2.217.7.1.2.7
		-- 1.3.6.1.4.1.2011.2.217.7.1.2.7
		sftpDir OBJECT-TYPE
			SYNTAX OCTET STRING
			MAX-ACCESS read-write
			STATUS current
			DESCRIPTION
				"Description."
			::= { ftp 8 }			

		
--  1.3.6.1.4.1.2011.2.217.7.1.2.4
		-- 1.3.6.1.4.1.2011.2.217.7.1.2.4
		sftpHostIP OBJECT-TYPE
			SYNTAX OCTET STRING
			MAX-ACCESS read-write
			STATUS current
			DESCRIPTION
				"Description."
			::= { ftp 4 } 
--  1.3.6.1.4.1.2011.2.217.7.1.2.7
		-- 1.3.6.1.4.1.2011.2.217.7.1.2.7
		sftpHostPort OBJECT-TYPE
			SYNTAX  Integer32
			MAX-ACCESS read-write
			STATUS current
			DESCRIPTION
				"Description."
			::= { ftp 7 }		

--  1.3.6.1.4.1.2011.2.217.7.1.2.5
		-- 1.3.6.1.4.1.2011.2.217.7.1.2.5
		agentFileOperation OBJECT-TYPE
			SYNTAX Integer32
			MAX-ACCESS write-only
			STATUS current
			DESCRIPTION
				"Description."
			::= { ftp 5 }

		
--  1.3.6.1.4.1.2011.2.217.7.1.2.6
		-- 1.3.6.1.4.1.2011.2.217.7.1.2.6
		upgradeQuery OBJECT-TYPE
			SYNTAX Integer32
			MAX-ACCESS read-only
			STATUS current
			DESCRIPTION
				"Description."
			::= { ftp 6 }

		
--  1.3.6.1.4.1.2011.2.217.7.1.3
		-- 1.3.6.1.4.1.2011.2.217.7.1.3
		systemControlStrategy OBJECT IDENTIFIER ::= { hwSystem 3 }

		
--  1.3.6.1.4.1.2011.2.217.7.1.3.1
		-- 1.3.6.1.4.1.2011.2.217.7.1.3.1
		proportionalValves1 OBJECT-TYPE
			SYNTAX Integer32
			MAX-ACCESS read-write
			STATUS current
			DESCRIPTION
				"Description."
			::= { systemControlStrategy 1 }

		
--  1.3.6.1.4.1.2011.2.217.7.1.3.2
		-- 1.3.6.1.4.1.2011.2.217.7.1.3.2
		proportionalValves2 OBJECT-TYPE
			SYNTAX Integer32
			MAX-ACCESS read-write
			STATUS current
			DESCRIPTION
				"Description."
			::= { systemControlStrategy 2 }

		
--  1.3.6.1.4.1.2011.2.217.7.1.3.3
		-- 1.3.6.1.4.1.2011.2.217.7.1.3.3
		temperatureAndHumidityStrategy OBJECT-TYPE
			SYNTAX Integer32
			MAX-ACCESS read-write
			STATUS current
			DESCRIPTION
				"Description."
			::= { systemControlStrategy 3 }

		
--  1.3.6.1.4.1.2011.2.217.7.1.3.4
		-- 1.3.6.1.4.1.2011.2.217.7.1.3.4
		drainagePump OBJECT-TYPE
			SYNTAX Integer32
			MAX-ACCESS read-write
			STATUS current
			DESCRIPTION
				"Description."
			::= { systemControlStrategy 4 }       

--  1.3.6.1.4.1.2011.2.217.7.1.3.5
		-- 1.3.6.1.4.1.2011.2.217.7.1.3.5
		pidT1 OBJECT-TYPE
			SYNTAX Integer32
			MAX-ACCESS read-write
			STATUS current
			DESCRIPTION
				"Description."
			::= { systemControlStrategy 5 }
			
--  1.3.6.1.4.1.2011.2.217.7.1.3.6
		-- 1.3.6.1.4.1.2011.2.217.7.1.3.6
		pidT2 OBJECT-TYPE
			SYNTAX Integer32
			MAX-ACCESS read-write
			STATUS current
			DESCRIPTION
				"Description."
			::= { systemControlStrategy 6 }        

--  1.3.6.1.4.1.2011.2.217.7.1.3.7
		-- 1.3.6.1.4.1.2011.2.217.7.1.3.7
		proportionalDelayTime OBJECT-TYPE
			SYNTAX Integer32
			MAX-ACCESS read-write
			STATUS current
			DESCRIPTION
				"Description."
			::= { systemControlStrategy 7 }
			
--  1.3.6.1.4.1.2011.2.217.7.1.3.8
		-- 1.3.6.1.4.1.2011.2.217.7.1.3.8
		pidDewpointTemperature OBJECT-TYPE
			SYNTAX Integer32
			MAX-ACCESS read-write
			STATUS current
			DESCRIPTION
				"Description."
			::= { systemControlStrategy 8 }

		
--  1.3.6.1.4.1.2011.2.217.7.2
		-- 1.3.6.1.4.1.2011.2.217.7.2
		hwSensor OBJECT IDENTIFIER ::= { hwLcs 2 }

		
--  1.3.6.1.4.1.2011.2.217.7.2.2
		-- 1.3.6.1.4.1.2011.2.217.7.2.2
		pump OBJECT IDENTIFIER ::= { hwSensor 2 }

		
--   1.3.6.1.4.1.2011.1.217.7.229.41175
-- 1.3.6.1.4.1.2011.2.217.7.2.2.9
		-- 1.3.6.1.4.1.2011.2.217.7.2.2.9
		drainPump0 OBJECT-TYPE
			SYNTAX Integer32
			MAX-ACCESS read-write
			STATUS current
			DESCRIPTION
				"Description."
			::= { pump 9 }
		
--  1.3.6.1.4.1.2011.2.217.7.2.2.11
		-- 1.3.6.1.4.1.2011.2.217.7.2.2.11
		drainPump1 OBJECT-TYPE
			SYNTAX Integer32
			MAX-ACCESS read-write
			STATUS current
			DESCRIPTION
				"Description."
			::= { pump 11 }
		
--  1.3.6.1.4.1.2011.2.217.7.2.3
		-- 1.3.6.1.4.1.2011.2.217.7.2.3
		photoelectricLevelSensor OBJECT IDENTIFIER ::= { hwSensor 3 }

		
--  1.3.6.1.4.1.2011.2.217.7.2.3.1
		-- 1.3.6.1.4.1.2011.2.217.7.2.3.1
		liquidLv0Value OBJECT-TYPE
			SYNTAX Integer32
			MAX-ACCESS read-only
			STATUS current
			DESCRIPTION
				"Description."
			::= { photoelectricLevelSensor 1 }

		
--  1.3.6.1.4.1.2011.2.217.7.2.3.2
		-- 1.3.6.1.4.1.2011.2.217.7.2.3.2
		liquidLv0Enable OBJECT-TYPE
			SYNTAX Integer32
			MAX-ACCESS read-write
			STATUS current
			DESCRIPTION
				"Description."
			::= { photoelectricLevelSensor 2 }

		
--  1.3.6.1.4.1.2011.2.217.7.2.3.3
		-- 1.3.6.1.4.1.2011.2.217.7.2.3.3
		liquidLv1Value OBJECT-TYPE
			SYNTAX Integer32
			MAX-ACCESS read-only
			STATUS current
			DESCRIPTION
				"Description."
			::= { photoelectricLevelSensor 3 }

		
--  1.3.6.1.4.1.2011.2.217.7.2.3.4
		-- 1.3.6.1.4.1.2011.2.217.7.2.3.4
		liquidLv1Enable OBJECT-TYPE
			SYNTAX Integer32
			MAX-ACCESS read-write
			STATUS current
			DESCRIPTION
				"Description."
			::= { photoelectricLevelSensor 4 }

		
--  1.3.6.1.4.1.2011.2.217.7.2.3.5
		-- 1.3.6.1.4.1.2011.2.217.7.2.3.5
		liquidLv2Value OBJECT-TYPE
			SYNTAX Integer32
			MAX-ACCESS read-only
			STATUS current
			DESCRIPTION
				"Description."
			::= { photoelectricLevelSensor 5 }

		
--  1.3.6.1.4.1.2011.2.217.7.2.3.6
		-- 1.3.6.1.4.1.2011.2.217.7.2.3.6
		liquidLv2Enable OBJECT-TYPE
			SYNTAX Integer32
			MAX-ACCESS read-write
			STATUS current
			DESCRIPTION
				"Description."
			::= { photoelectricLevelSensor 6 }

		
--  1.3.6.1.4.1.2011.2.217.7.2.3.7
		-- 1.3.6.1.4.1.2011.2.217.7.2.3.7
		liquidLv3Value OBJECT-TYPE
			SYNTAX Integer32
			MAX-ACCESS read-only
			STATUS current
			DESCRIPTION
				"Description."
			::= { photoelectricLevelSensor 7 }

		
--  1.3.6.1.4.1.2011.2.217.7.2.3.8
		-- 1.3.6.1.4.1.2011.2.217.7.2.3.8
		liquidLv3Enable OBJECT-TYPE
			SYNTAX Integer32
			MAX-ACCESS read-write
			STATUS current
			DESCRIPTION
				"Description."
			::= { photoelectricLevelSensor 8 }
			
--  1.3.6.1.4.1.2011.2.217.7.2.3.9
		-- 1.3.6.1.4.1.2011.2.217.7.2.3.9
		liquidLv4Value OBJECT-TYPE
			SYNTAX Integer32
			MAX-ACCESS read-only
			STATUS current
			DESCRIPTION
				"Description."
			::= { photoelectricLevelSensor 9 }

		
--  1.3.6.1.4.1.2011.2.217.7.2.3.10
		-- 1.3.6.1.4.1.2011.2.217.7.2.3.10
		liquidLv4Enable OBJECT-TYPE
			SYNTAX Integer32
			MAX-ACCESS read-write
			STATUS current
			DESCRIPTION
				"Description."
			::= { photoelectricLevelSensor 10 }		

--  1.3.6.1.4.1.2011.2.217.7.2.3.11
		-- 1.3.6.1.4.1.2011.2.217.7.2.3.11
		liquidLv5Value OBJECT-TYPE
			SYNTAX Integer32
			MAX-ACCESS read-only
			STATUS current
			DESCRIPTION
				"Description."
			::= { photoelectricLevelSensor 11 }

		
--  1.3.6.1.4.1.2011.2.217.7.2.3.12
		-- 1.3.6.1.4.1.2011.2.217.7.2.3.12
		liquidLv5Enable OBJECT-TYPE
			SYNTAX Integer32
			MAX-ACCESS read-write
			STATUS current
			DESCRIPTION
				"Description."
			::= { photoelectricLevelSensor 12 }		

--  1.3.6.1.4.1.2011.2.217.7.2.3.13
		-- 1.3.6.1.4.1.2011.2.217.7.2.3.13
		liquidLv6Value OBJECT-TYPE
			SYNTAX Integer32
			MAX-ACCESS read-only
			STATUS current
			DESCRIPTION
				"Description."
			::= { photoelectricLevelSensor 13 }

		
--  1.3.6.1.4.1.2011.2.217.7.2.3.14
		-- 1.3.6.1.4.1.2011.2.217.7.2.3.14
		liquidLv6Enable OBJECT-TYPE
			SYNTAX Integer32
			MAX-ACCESS read-write
			STATUS current
			DESCRIPTION
				"Description."
			::= { photoelectricLevelSensor 14 }		

--  1.3.6.1.4.1.2011.2.217.7.2.3.15
		-- 1.3.6.1.4.1.2011.2.217.7.2.3.15
		liquidLv7Value OBJECT-TYPE
			SYNTAX Integer32
			MAX-ACCESS read-only
			STATUS current
			DESCRIPTION
				"Description."
			::= { photoelectricLevelSensor 15 }

		
--  1.3.6.1.4.1.2011.2.217.7.2.3.16
		-- 1.3.6.1.4.1.2011.2.217.7.2.3.16
		liquidLv7Enable OBJECT-TYPE
			SYNTAX Integer32
			MAX-ACCESS read-write
			STATUS current
			DESCRIPTION
				"Description."
			::= { photoelectricLevelSensor 16 }		

--  1.3.6.1.4.1.2011.2.217.7.2.3.17
		-- 1.3.6.1.4.1.2011.2.217.7.2.3.17
		liquidLv8Value OBJECT-TYPE
			SYNTAX Integer32
			MAX-ACCESS read-only
			STATUS current
			DESCRIPTION
				"Description."
			::= { photoelectricLevelSensor 17 }

		
--  1.3.6.1.4.1.2011.2.217.7.2.3.18
		-- 1.3.6.1.4.1.2011.2.217.7.2.3.18
		liquidLv8Enable OBJECT-TYPE
			SYNTAX Integer32
			MAX-ACCESS read-write
			STATUS current
			DESCRIPTION
				"Description."
			::= { photoelectricLevelSensor 18 }	
			
--  1.3.6.1.4.1.2011.2.217.7.2.3.19
		-- 1.3.6.1.4.1.2011.2.217.7.2.3.19
		liquidLv9Value OBJECT-TYPE
			SYNTAX Integer32
			MAX-ACCESS read-only
			STATUS current
			DESCRIPTION
				"Description."
			::= { photoelectricLevelSensor 19 }

		
--  1.3.6.1.4.1.2011.2.217.7.2.3.20
		-- 1.3.6.1.4.1.2011.2.217.7.2.3.20
		liquidLv9Enable OBJECT-TYPE
			SYNTAX Integer32
			MAX-ACCESS read-write
			STATUS current
			DESCRIPTION
				"Description."
			::= { photoelectricLevelSensor 20 }	
		
--  1.3.6.1.4.1.2011.2.217.7.2.4
		-- 1.3.6.1.4.1.2011.2.217.7.2.4
		floatLevelSensor OBJECT IDENTIFIER ::= { hwSensor 4 }

		
--  1.3.6.1.4.1.2011.2.217.7.2.4.1
		-- 1.3.6.1.4.1.2011.2.217.7.2.4.1
		floatLiquidLv0Value OBJECT-TYPE
			SYNTAX Integer32
			MAX-ACCESS read-only
			STATUS current
			DESCRIPTION
				"Description."
			::= { floatLevelSensor 1 }

		
--  1.3.6.1.4.1.2011.2.217.7.2.4.2
		-- 1.3.6.1.4.1.2011.2.217.7.2.4.2
		floatLiquidLv0Enable OBJECT-TYPE
			SYNTAX Integer32
			MAX-ACCESS read-write
			STATUS current
			DESCRIPTION
				"Description."
			::= { floatLevelSensor 2 }

		
--  1.3.6.1.4.1.2011.2.217.7.2.4.3
		-- 1.3.6.1.4.1.2011.2.217.7.2.4.3
		floatLiquidLv1Value OBJECT-TYPE
			SYNTAX Integer32
			MAX-ACCESS read-only
			STATUS current
			DESCRIPTION
				"Description."
			::= { floatLevelSensor 3 }

		
--  1.3.6.1.4.1.2011.2.217.7.2.4.4
		-- 1.3.6.1.4.1.2011.2.217.7.2.4.4
		floatLiquidLv1Enable OBJECT-TYPE
			SYNTAX Integer32
			MAX-ACCESS read-write
			STATUS current
			DESCRIPTION
				"Description."
			::= { floatLevelSensor 4 }

		
--  1.3.6.1.4.1.2011.2.217.7.2.4.5
		-- 1.3.6.1.4.1.2011.2.217.7.2.4.5
		floatLiquidLv2Value OBJECT-TYPE
			SYNTAX Integer32
			MAX-ACCESS read-only
			STATUS current
			DESCRIPTION
				"Description."
			::= { floatLevelSensor 5 }

		
--  1.3.6.1.4.1.2011.2.217.7.2.4.6
		-- 1.3.6.1.4.1.2011.2.217.7.2.4.6
		floatLiquidLv2Enable OBJECT-TYPE
			SYNTAX Integer32
			MAX-ACCESS read-write
			STATUS current
			DESCRIPTION
				"Description."
			::= { floatLevelSensor 6 }

		
--  1.3.6.1.4.1.2011.2.217.7.2.4.7
		-- 1.3.6.1.4.1.2011.2.217.7.2.4.7
		floatLiquidLv3Value OBJECT-TYPE
			SYNTAX Integer32
			MAX-ACCESS read-only
			STATUS current
			DESCRIPTION
				"Description."
			::= { floatLevelSensor 7 }

		
--  1.3.6.1.4.1.2011.2.217.7.2.4.8
		-- 1.3.6.1.4.1.2011.2.217.7.2.4.8
		floatLiquidLv3Enable OBJECT-TYPE
			SYNTAX Integer32
			MAX-ACCESS read-write
			STATUS current
			DESCRIPTION
				"Description."
			::= { floatLevelSensor 8 }

		
--  1.3.6.1.4.1.2011.2.217.7.2.6
		-- 1.3.6.1.4.1.2011.2.217.7.2.6
		leakage OBJECT IDENTIFIER ::= { hwSensor 6 }

--  1.3.6.1.4.1.2011.2.217.7.2.6.1
		-- 1.3.6.1.4.1.2011.2.217.7.2.6.1
		leakage1Check OBJECT-TYPE
			SYNTAX Integer32
			MAX-ACCESS read-write
			STATUS current
			DESCRIPTION
				"Description."
			::= { leakage 1 }

		
--  1.3.6.1.4.1.2011.2.217.7.2.6.2
		-- 1.3.6.1.4.1.2011.2.217.7.2.6.2
		leakage1AlarmEnable OBJECT-TYPE
			SYNTAX Integer32
			MAX-ACCESS read-write
			STATUS current
			DESCRIPTION
				"Description."
			::= { leakage 2 }
			
--  1.3.6.1.4.1.2011.2.217.7.2.6.3
		-- 1.3.6.1.4.1.2011.2.217.7.2.6.3
		leakage2Check OBJECT-TYPE
			SYNTAX Integer32
			MAX-ACCESS read-write
			STATUS current
			DESCRIPTION
				"Description."
			::= { leakage 3 }

		
--  1.3.6.1.4.1.2011.2.217.7.2.6.4
		-- 1.3.6.1.4.1.2011.2.217.7.2.6.4
		leakage2AlarmEnable OBJECT-TYPE
			SYNTAX Integer32
			MAX-ACCESS read-write
			STATUS current
			DESCRIPTION
				"Description."
			::= { leakage 4 }			
			
--  1.3.6.1.4.1.2011.2.217.7.2.6.7
		-- 1.3.6.1.4.1.2011.2.217.7.2.6.7
		leakage3Check OBJECT-TYPE
			SYNTAX Integer32
			MAX-ACCESS read-write
			STATUS current
			DESCRIPTION
				"Description."
			::= { leakage 7 }

		
--  1.3.6.1.4.1.2011.2.217.7.2.6.8
		-- 1.3.6.1.4.1.2011.2.217.7.2.6.8
		leakage3AlarmEnable OBJECT-TYPE
			SYNTAX Integer32
			MAX-ACCESS read-write
			STATUS current
			DESCRIPTION
				"Description."
			::= { leakage 8 }

		
--  1.3.6.1.4.1.2011.2.217.7.2.7
		-- 1.3.6.1.4.1.2011.2.217.7.2.7
		proportional OBJECT IDENTIFIER ::= { hwSensor 7 }

		
--  1.3.6.1.4.1.2011.2.217.7.2.7.3
		-- 1.3.6.1.4.1.2011.2.217.7.2.7.3
		proportionalLv1Value OBJECT-TYPE
			SYNTAX Integer32
			MAX-ACCESS read-write
			STATUS current
			DESCRIPTION
				"Description."
			::= { proportional 3 }

		
--  1.3.6.1.4.1.2011.2.217.7.2.7.4
		-- 1.3.6.1.4.1.2011.2.217.7.2.7.4
		proportionalLv1Enable OBJECT-TYPE
			SYNTAX Integer32
			MAX-ACCESS read-write
			STATUS current
			DESCRIPTION
				"Description."
			::= { proportional 4 }

		
--  1.3.6.1.4.1.2011.2.217.7.2.7.5
		-- 1.3.6.1.4.1.2011.2.217.7.2.7.5
		proportionalLv2Value OBJECT-TYPE
			SYNTAX Integer32
			MAX-ACCESS read-write
			STATUS current
			DESCRIPTION
				"Description."
			::= { proportional 5 }

		
--  1.3.6.1.4.1.2011.2.217.7.2.7.6
		-- 1.3.6.1.4.1.2011.2.217.7.2.7.6
		proportionalLv2Enable OBJECT-TYPE
			SYNTAX Integer32
			MAX-ACCESS read-write
			STATUS current
			DESCRIPTION
				"Description."
			::= { proportional 6 }

--  1.3.6.1.4.1.2011.2.217.7.2.7.14
		-- 1.3.6.1.4.1.2011.2.217.7.2.7.14
		proportionalLV1FeedbackPosition OBJECT-TYPE
			SYNTAX Integer32
			MAX-ACCESS read-write
			STATUS current
			DESCRIPTION
				"Description."
			::= { proportional 14 }
			
--  1.3.6.1.4.1.2011.2.217.7.2.7.15
		-- 1.3.6.1.4.1.2011.2.217.7.2.7.15
		proportionalLV2FeedbackPosition OBJECT-TYPE
			SYNTAX Integer32
			MAX-ACCESS read-write
			STATUS current
			DESCRIPTION
				"Description."
			::= { proportional 15 }			

		
--  1.3.6.1.4.1.2011.2.217.7.2.11
		-- 1.3.6.1.4.1.2011.2.217.7.2.11
		temperatureAndHumidity OBJECT IDENTIFIER ::= { hwSensor 11 }

		
--  1.3.6.1.4.1.2011.2.217.7.2.11.1
		-- 1.3.6.1.4.1.2011.2.217.7.2.11.1
		humidity0 OBJECT-TYPE
			SYNTAX Integer32
			MAX-ACCESS read-only
			STATUS current
			DESCRIPTION
				"Description."
			::= { temperatureAndHumidity 1 }

		
--  1.3.6.1.4.1.2011.2.217.7.2.11.2
		-- 1.3.6.1.4.1.2011.2.217.7.2.11.2
		temperature0 OBJECT-TYPE
			SYNTAX Integer32
			MAX-ACCESS read-only
			STATUS current
			DESCRIPTION
				"Description."
			::= { temperatureAndHumidity 2 }

		
--  1.3.6.1.4.1.2011.2.217.7.2.11.3
		-- 1.3.6.1.4.1.2011.2.217.7.2.11.3
		humidity0upLimitValue OBJECT-TYPE
			SYNTAX Integer32
			MAX-ACCESS read-write
			STATUS current
			DESCRIPTION
				"Description."
			::= { temperatureAndHumidity 3 }

		
--  1.3.6.1.4.1.2011.2.217.7.2.11.4
		-- 1.3.6.1.4.1.2011.2.217.7.2.11.4
		humidity0downLimitValue OBJECT-TYPE
			SYNTAX Integer32
			MAX-ACCESS read-write
			STATUS current
			DESCRIPTION
				"Description."
			::= { temperatureAndHumidity 4 }

		
--  1.3.6.1.4.1.2011.2.217.7.2.11.5
		-- 1.3.6.1.4.1.2011.2.217.7.2.11.5
		temperature0upLimitValue OBJECT-TYPE
			SYNTAX Integer32
			MAX-ACCESS read-write
			STATUS current
			DESCRIPTION
				"Description."
			::= { temperatureAndHumidity 5 }

		
--  1.3.6.1.4.1.2011.2.217.7.2.11.6
		-- 1.3.6.1.4.1.2011.2.217.7.2.11.6
		temperature0downLimitValue OBJECT-TYPE
			SYNTAX Integer32
			MAX-ACCESS read-write
			STATUS current
			DESCRIPTION
				"Description."
			::= { temperatureAndHumidity 6 }

		
--  1.3.6.1.4.1.2011.2.217.7.2.11.7
		-- 1.3.6.1.4.1.2011.2.217.7.2.11.7
		humidity0upLimitAlarmEnable OBJECT-TYPE
			SYNTAX Integer32
			MAX-ACCESS read-write
			STATUS current
			DESCRIPTION
				"Description."
			::= { temperatureAndHumidity 7 }

		
--  1.3.6.1.4.1.2011.2.217.7.2.11.8
		-- 1.3.6.1.4.1.2011.2.217.7.2.11.8
		humidity0downLimitAlarmEnable OBJECT-TYPE
			SYNTAX Integer32
			MAX-ACCESS read-write
			STATUS current
			DESCRIPTION
				"Description."
			::= { temperatureAndHumidity 8 }

		
--  1.3.6.1.4.1.2011.2.217.7.2.11.9
		-- 1.3.6.1.4.1.2011.2.217.7.2.11.9
		temperature0upLimitAlarmEnable OBJECT-TYPE
			SYNTAX Integer32
			MAX-ACCESS read-write
			STATUS current
			DESCRIPTION
				"Description."
			::= { temperatureAndHumidity 9 }

		
--  1.3.6.1.4.1.2011.2.217.7.2.11.10
		-- 1.3.6.1.4.1.2011.2.217.7.2.11.10
		temperature0downLimitAlarmEnable OBJECT-TYPE
			SYNTAX Integer32
			MAX-ACCESS read-write
			STATUS current
			DESCRIPTION
				"Description."
			::= { temperatureAndHumidity 10 }

		
--  1.3.6.1.4.1.2011.2.217.7.2.11.11
		-- 1.3.6.1.4.1.2011.2.217.7.2.11.11
		fault0 OBJECT-TYPE
			SYNTAX Integer32
			MAX-ACCESS read-write
			STATUS current
			DESCRIPTION
				"Description."
			::= { temperatureAndHumidity 11 }

		
--  1.3.6.1.4.1.2011.2.217.7.2.11.12
		-- 1.3.6.1.4.1.2011.2.217.7.2.11.12
		humidity1 OBJECT-TYPE
			SYNTAX Integer32
			MAX-ACCESS read-only
			STATUS current
			DESCRIPTION
				"Description."
			::= { temperatureAndHumidity 12 }

		
--  1.3.6.1.4.1.2011.2.217.7.2.11.13
		-- 1.3.6.1.4.1.2011.2.217.7.2.11.13
		temperature1 OBJECT-TYPE
			SYNTAX Integer32
			MAX-ACCESS read-only
			STATUS current
			DESCRIPTION
				"Description."
			::= { temperatureAndHumidity 13 }

		
--  1.3.6.1.4.1.2011.2.217.7.2.11.14
		-- 1.3.6.1.4.1.2011.2.217.7.2.11.14
		humidity1upLimitValue OBJECT-TYPE
			SYNTAX Integer32
			MAX-ACCESS read-write
			STATUS current
			DESCRIPTION
				"Description."
			::= { temperatureAndHumidity 14 }

		
--  1.3.6.1.4.1.2011.2.217.7.2.11.15
		-- 1.3.6.1.4.1.2011.2.217.7.2.11.15
		humidity1downLimitValue OBJECT-TYPE
			SYNTAX Integer32
			MAX-ACCESS read-write
			STATUS current
			DESCRIPTION
				"Description."
			::= { temperatureAndHumidity 15 }

		
--  1.3.6.1.4.1.2011.2.217.7.2.11.16
		-- 1.3.6.1.4.1.2011.2.217.7.2.11.16
		temperature1upLimitValue OBJECT-TYPE
			SYNTAX Integer32
			MAX-ACCESS read-write
			STATUS current
			DESCRIPTION
				"Description."
			::= { temperatureAndHumidity 16 }

		
--  1.3.6.1.4.1.2011.2.217.7.2.11.17
		-- 1.3.6.1.4.1.2011.2.217.7.2.11.17
		temperature1downLimitValue OBJECT-TYPE
			SYNTAX Integer32
			MAX-ACCESS read-write
			STATUS current
			DESCRIPTION
				"Description."
			::= { temperatureAndHumidity 17 }

		
--  1.3.6.1.4.1.2011.2.217.7.2.11.18
		-- 1.3.6.1.4.1.2011.2.217.7.2.11.18
		humidity1upLimitAlarmEnable OBJECT-TYPE
			SYNTAX Integer32
			MAX-ACCESS read-write
			STATUS current
			DESCRIPTION
				"Description."
			::= { temperatureAndHumidity 18 }

		
--  1.3.6.1.4.1.2011.2.217.7.2.11.19
		-- 1.3.6.1.4.1.2011.2.217.7.2.11.19
		humidity1downLimitAlarmEnable OBJECT-TYPE
			SYNTAX Integer32
			MAX-ACCESS read-write
			STATUS current
			DESCRIPTION
				"Description."
			::= { temperatureAndHumidity 19 }

		
--  1.3.6.1.4.1.2011.2.217.7.2.11.20
		-- 1.3.6.1.4.1.2011.2.217.7.2.11.20
		temperature1upLimitAlarmEnable OBJECT-TYPE
			SYNTAX Integer32
			MAX-ACCESS read-write
			STATUS current
			DESCRIPTION
				"Description."
			::= { temperatureAndHumidity 20 }

		
--  1.3.6.1.4.1.2011.2.217.7.2.11.21
		-- 1.3.6.1.4.1.2011.2.217.7.2.11.21
		temperature1downLimitAlarmEnable OBJECT-TYPE
			SYNTAX Integer32
			MAX-ACCESS read-write
			STATUS current
			DESCRIPTION
				"Description."
			::= { temperatureAndHumidity 21 }

		
--  1.3.6.1.4.1.2011.2.217.7.2.11.22
		-- 1.3.6.1.4.1.2011.2.217.7.2.11.22
		fault1 OBJECT-TYPE
			SYNTAX Integer32
			MAX-ACCESS read-write
			STATUS current
			DESCRIPTION
				"Description."
			::= { temperatureAndHumidity 22 }

		
--  1.3.6.1.4.1.2011.2.217.7.2.11.23
		-- 1.3.6.1.4.1.2011.2.217.7.2.11.23
		humidity2 OBJECT-TYPE
			SYNTAX Integer32
			MAX-ACCESS read-only
			STATUS current
			DESCRIPTION
				"Description."
			::= { temperatureAndHumidity 23 }

		
--  1.3.6.1.4.1.2011.2.217.7.2.11.24
		-- 1.3.6.1.4.1.2011.2.217.7.2.11.24
		temperature2 OBJECT-TYPE
			SYNTAX Integer32
			MAX-ACCESS read-only
			STATUS current
			DESCRIPTION
				"Description."
			::= { temperatureAndHumidity 24 }

		
--  1.3.6.1.4.1.2011.2.217.7.2.11.25
		-- 1.3.6.1.4.1.2011.2.217.7.2.11.25
		humidity2upLimitValue OBJECT-TYPE
			SYNTAX Integer32
			MAX-ACCESS read-write
			STATUS current
			DESCRIPTION
				"Description."
			::= { temperatureAndHumidity 25 }

		
--  1.3.6.1.4.1.2011.2.217.7.2.11.26
		-- 1.3.6.1.4.1.2011.2.217.7.2.11.26
		humidity2downLimitValue OBJECT-TYPE
			SYNTAX Integer32
			MAX-ACCESS read-write
			STATUS current
			DESCRIPTION
				"Description."
			::= { temperatureAndHumidity 26 }

		
--  1.3.6.1.4.1.2011.2.217.7.2.11.27
		-- 1.3.6.1.4.1.2011.2.217.7.2.11.27
		temperature2upLimitValue OBJECT-TYPE
			SYNTAX Integer32
			MAX-ACCESS read-write
			STATUS current
			DESCRIPTION
				"Description."
			::= { temperatureAndHumidity 27 }

		
--  1.3.6.1.4.1.2011.2.217.7.2.11.28
		-- 1.3.6.1.4.1.2011.2.217.7.2.11.28
		temperature2downLimitValue OBJECT-TYPE
			SYNTAX Integer32
			MAX-ACCESS read-write
			STATUS current
			DESCRIPTION
				"Description."
			::= { temperatureAndHumidity 28 }

		
--  1.3.6.1.4.1.2011.2.217.7.2.11.29
		-- 1.3.6.1.4.1.2011.2.217.7.2.11.29
		humidity2upLimitAlarmEnable OBJECT-TYPE
			SYNTAX Integer32
			MAX-ACCESS read-write
			STATUS current
			DESCRIPTION
				"Description."
			::= { temperatureAndHumidity 29 }

		
--  1.3.6.1.4.1.2011.2.217.7.2.11.30
		-- 1.3.6.1.4.1.2011.2.217.7.2.11.30
		humidity2downLimitAlarmEnable OBJECT-TYPE
			SYNTAX Integer32
			MAX-ACCESS read-write
			STATUS current
			DESCRIPTION
				"Description."
			::= { temperatureAndHumidity 30 }

		
--  1.3.6.1.4.1.2011.2.217.7.2.11.31
		-- 1.3.6.1.4.1.2011.2.217.7.2.11.31
		temperature2upLimitAlarmEnable OBJECT-TYPE
			SYNTAX Integer32
			MAX-ACCESS read-write
			STATUS current
			DESCRIPTION
				"Description."
			::= { temperatureAndHumidity 31 }

		
--  1.3.6.1.4.1.2011.2.217.7.2.11.32
		-- 1.3.6.1.4.1.2011.2.217.7.2.11.32
		temperature2downLimitAlarmEnable OBJECT-TYPE
			SYNTAX Integer32
			MAX-ACCESS read-write
			STATUS current
			DESCRIPTION
				"Description."
			::= { temperatureAndHumidity 32 }

		
--  1.3.6.1.4.1.2011.2.217.7.2.11.33
		-- 1.3.6.1.4.1.2011.2.217.7.2.11.33
		fault2 OBJECT-TYPE
			SYNTAX Integer32
			MAX-ACCESS read-write
			STATUS current
			DESCRIPTION
				"Description."
			::= { temperatureAndHumidity 33 }

		
--  1.3.6.1.4.1.2011.2.217.7.2.11.34
		-- 1.3.6.1.4.1.2011.2.217.7.2.11.34
		humidity3 OBJECT-TYPE
			SYNTAX Integer32
			MAX-ACCESS read-only
			STATUS current
			DESCRIPTION
				"Description."
			::= { temperatureAndHumidity 34 }

		
--  1.3.6.1.4.1.2011.2.217.7.2.11.35
		-- 1.3.6.1.4.1.2011.2.217.7.2.11.35
		temperature3 OBJECT-TYPE
			SYNTAX Integer32
			MAX-ACCESS read-only
			STATUS current
			DESCRIPTION
				"Description."
			::= { temperatureAndHumidity 35 }

		
--  1.3.6.1.4.1.2011.2.217.7.2.11.36
		-- 1.3.6.1.4.1.2011.2.217.7.2.11.36
		humidity3upLimitValue OBJECT-TYPE
			SYNTAX Integer32
			MAX-ACCESS read-write
			STATUS current
			DESCRIPTION
				"Description."
			::= { temperatureAndHumidity 36 }

		
--  1.3.6.1.4.1.2011.2.217.7.2.11.37
		-- 1.3.6.1.4.1.2011.2.217.7.2.11.37
		humidity3downLimitValue OBJECT-TYPE
			SYNTAX Integer32
			MAX-ACCESS read-write
			STATUS current
			DESCRIPTION
				"Description."
			::= { temperatureAndHumidity 37 }

		
--  1.3.6.1.4.1.2011.2.217.7.2.11.38
		-- 1.3.6.1.4.1.2011.2.217.7.2.11.38
		temperature3upLimitValue OBJECT-TYPE
			SYNTAX Integer32
			MAX-ACCESS read-write
			STATUS current
			DESCRIPTION
				"Description."
			::= { temperatureAndHumidity 38 }

		
--  1.3.6.1.4.1.2011.2.217.7.2.11.39
		-- 1.3.6.1.4.1.2011.2.217.7.2.11.39
		temperature3downLimitValue OBJECT-TYPE
			SYNTAX Integer32
			MAX-ACCESS read-write
			STATUS current
			DESCRIPTION
				"Description."
			::= { temperatureAndHumidity 39 }

		
--  1.3.6.1.4.1.2011.2.217.7.2.11.40
		-- 1.3.6.1.4.1.2011.2.217.7.2.11.40
		humidity3upLimitAlarmEnable OBJECT-TYPE
			SYNTAX Integer32
			MAX-ACCESS read-write
			STATUS current
			DESCRIPTION
				"Description."
			::= { temperatureAndHumidity 40 }

		
--  1.3.6.1.4.1.2011.2.217.7.2.11.41
		-- 1.3.6.1.4.1.2011.2.217.7.2.11.41
		humidity3downLimitAlarmEnable OBJECT-TYPE
			SYNTAX Integer32
			MAX-ACCESS read-write
			STATUS current
			DESCRIPTION
				"Description."
			::= { temperatureAndHumidity 41 }

		
--  1.3.6.1.4.1.2011.2.217.7.2.11.42
		-- 1.3.6.1.4.1.2011.2.217.7.2.11.42
		temperature3upLimitAlarmEnable OBJECT-TYPE
			SYNTAX Integer32
			MAX-ACCESS read-write
			STATUS current
			DESCRIPTION
				"Description."
			::= { temperatureAndHumidity 42 }

		
--  1.3.6.1.4.1.2011.2.217.7.2.11.43
		-- 1.3.6.1.4.1.2011.2.217.7.2.11.43
		temperature3downLimitAlarmEnable OBJECT-TYPE
			SYNTAX Integer32
			MAX-ACCESS read-write
			STATUS current
			DESCRIPTION
				"Description."
			::= { temperatureAndHumidity 43 }

		
--  1.3.6.1.4.1.2011.2.217.7.2.11.44
		-- 1.3.6.1.4.1.2011.2.217.7.2.11.44
		fault3 OBJECT-TYPE
			SYNTAX Integer32
			MAX-ACCESS read-write
			STATUS current
			DESCRIPTION
				"Description."
			::= { temperatureAndHumidity 44 }

		
--  1.3.6.1.4.1.2011.2.217.7.2.11.45
		-- 1.3.6.1.4.1.2011.2.217.7.2.11.45
		humidity4 OBJECT-TYPE
			SYNTAX Integer32
			MAX-ACCESS read-only
			STATUS current
			DESCRIPTION
				"Description."
			::= { temperatureAndHumidity 45 }

		
--  1.3.6.1.4.1.2011.2.217.7.2.11.46
		-- 1.3.6.1.4.1.2011.2.217.7.2.11.46
		temperature4 OBJECT-TYPE
			SYNTAX Integer32
			MAX-ACCESS read-only
			STATUS current
			DESCRIPTION
				"Description."
			::= { temperatureAndHumidity 46 }

		
--  1.3.6.1.4.1.2011.2.217.7.2.11.47
		-- 1.3.6.1.4.1.2011.2.217.7.2.11.47
		humidity4upLimitValue OBJECT-TYPE
			SYNTAX Integer32
			MAX-ACCESS read-write
			STATUS current
			DESCRIPTION
				"Description."
			::= { temperatureAndHumidity 47 }

		
--  1.3.6.1.4.1.2011.2.217.7.2.11.48
		-- 1.3.6.1.4.1.2011.2.217.7.2.11.48
		humidity4downLimitValue OBJECT-TYPE
			SYNTAX Integer32
			MAX-ACCESS read-write
			STATUS current
			DESCRIPTION
				"Description."
			::= { temperatureAndHumidity 48 }

		
--  1.3.6.1.4.1.2011.2.217.7.2.11.49
		-- 1.3.6.1.4.1.2011.2.217.7.2.11.49
		temperature4upLimitValue OBJECT-TYPE
			SYNTAX Integer32
			MAX-ACCESS read-write
			STATUS current
			DESCRIPTION
				"Description."
			::= { temperatureAndHumidity 49 }

		
--  1.3.6.1.4.1.2011.2.217.7.2.11.50
		-- 1.3.6.1.4.1.2011.2.217.7.2.11.50
		temperature4downLimitValue OBJECT-TYPE
			SYNTAX Integer32
			MAX-ACCESS read-write
			STATUS current
			DESCRIPTION
				"Description."
			::= { temperatureAndHumidity 50 }

		
--  1.3.6.1.4.1.2011.2.217.7.2.11.51
		-- 1.3.6.1.4.1.2011.2.217.7.2.11.51
		humidity4upLimitAlarmEnable OBJECT-TYPE
			SYNTAX Integer32
			MAX-ACCESS read-write
			STATUS current
			DESCRIPTION
				"Description."
			::= { temperatureAndHumidity 51 }

		
--  1.3.6.1.4.1.2011.2.217.7.2.11.52
		-- 1.3.6.1.4.1.2011.2.217.7.2.11.52
		humidity4downLimitAlarmEnable OBJECT-TYPE
			SYNTAX Integer32
			MAX-ACCESS read-write
			STATUS current
			DESCRIPTION
				"Description."
			::= { temperatureAndHumidity 52 }

		
--  1.3.6.1.4.1.2011.2.217.7.2.11.53
		-- 1.3.6.1.4.1.2011.2.217.7.2.11.53
		temperature4upLimitAlarmEnable OBJECT-TYPE
			SYNTAX Integer32
			MAX-ACCESS read-write
			STATUS current
			DESCRIPTION
				"Description."
			::= { temperatureAndHumidity 53 }

		
--  1.3.6.1.4.1.2011.2.217.7.2.11.54
		-- 1.3.6.1.4.1.2011.2.217.7.2.11.54
		temperature4downLimitAlarmEnable OBJECT-TYPE
			SYNTAX Integer32
			MAX-ACCESS read-write
			STATUS current
			DESCRIPTION
				"Description."
			::= { temperatureAndHumidity 54 }

		
--  1.3.6.1.4.1.2011.2.217.7.2.11.55
		-- 1.3.6.1.4.1.2011.2.217.7.2.11.55
		fault4 OBJECT-TYPE
			SYNTAX Integer32
			MAX-ACCESS read-write
			STATUS current
			DESCRIPTION
				"Description."
			::= { temperatureAndHumidity 55 }

		
--  1.3.6.1.4.1.2011.2.217.7.2.11.56
		-- 1.3.6.1.4.1.2011.2.217.7.2.11.56
		humidity5 OBJECT-TYPE
			SYNTAX Integer32
			MAX-ACCESS read-only
			STATUS current
			DESCRIPTION
				"Description."
			::= { temperatureAndHumidity 56 }

		
--  1.3.6.1.4.1.2011.2.217.7.2.11.57
		-- 1.3.6.1.4.1.2011.2.217.7.2.11.57
		temperature5 OBJECT-TYPE
			SYNTAX Integer32
			MAX-ACCESS read-only
			STATUS current
			DESCRIPTION
				"Description."
			::= { temperatureAndHumidity 57 }

		
--  1.3.6.1.4.1.2011.2.217.7.2.11.58
		-- 1.3.6.1.4.1.2011.2.217.7.2.11.58
		humidity5upLimitValue OBJECT-TYPE
			SYNTAX Integer32
			MAX-ACCESS read-write
			STATUS current
			DESCRIPTION
				"Description."
			::= { temperatureAndHumidity 58 }

		
--  1.3.6.1.4.1.2011.2.217.7.2.11.59
		-- 1.3.6.1.4.1.2011.2.217.7.2.11.59
		humidity5downLimitValue OBJECT-TYPE
			SYNTAX Integer32
			MAX-ACCESS read-write
			STATUS current
			DESCRIPTION
				"Description."
			::= { temperatureAndHumidity 59 }

		
--  1.3.6.1.4.1.2011.2.217.7.2.11.60
		-- 1.3.6.1.4.1.2011.2.217.7.2.11.60
		temperature5upLimitValue OBJECT-TYPE
			SYNTAX Integer32
			MAX-ACCESS read-write
			STATUS current
			DESCRIPTION
				"Description."
			::= { temperatureAndHumidity 60 }

		
--  1.3.6.1.4.1.2011.2.217.7.2.11.61
		-- 1.3.6.1.4.1.2011.2.217.7.2.11.61
		temperature5downLimitValue OBJECT-TYPE
			SYNTAX Integer32
			MAX-ACCESS read-write
			STATUS current
			DESCRIPTION
				"Description."
			::= { temperatureAndHumidity 61 }

		
--  1.3.6.1.4.1.2011.2.217.7.2.11.62
		-- 1.3.6.1.4.1.2011.2.217.7.2.11.62
		humidity5upLimitAlarmEnable OBJECT-TYPE
			SYNTAX Integer32
			MAX-ACCESS read-write
			STATUS current
			DESCRIPTION
				"Description."
			::= { temperatureAndHumidity 62 }

		
--  1.3.6.1.4.1.2011.2.217.7.2.11.63
		-- 1.3.6.1.4.1.2011.2.217.7.2.11.63
		humidity5downLimitAlarmEnable OBJECT-TYPE
			SYNTAX Integer32
			MAX-ACCESS read-write
			STATUS current
			DESCRIPTION
				"Description."
			::= { temperatureAndHumidity 63 }

		
--  1.3.6.1.4.1.2011.2.217.7.2.11.64
		-- 1.3.6.1.4.1.2011.2.217.7.2.11.64
		temperature5upLimitAlarmEnable OBJECT-TYPE
			SYNTAX Integer32
			MAX-ACCESS read-write
			STATUS current
			DESCRIPTION
				"Description."
			::= { temperatureAndHumidity 64 }

		
--  1.3.6.1.4.1.2011.2.217.7.2.11.65
		-- 1.3.6.1.4.1.2011.2.217.7.2.11.65
		temperature5downLimitAlarmEnable OBJECT-TYPE
			SYNTAX Integer32
			MAX-ACCESS read-write
			STATUS current
			DESCRIPTION
				"Description."
			::= { temperatureAndHumidity 65 }

		
--  1.3.6.1.4.1.2011.2.217.7.2.11.66
		-- 1.3.6.1.4.1.2011.2.217.7.2.11.66
		fault5 OBJECT-TYPE
			SYNTAX Integer32
			MAX-ACCESS read-write
			STATUS current
			DESCRIPTION
				"Description."
			::= { temperatureAndHumidity 66 }

		
--  1.3.6.1.4.1.2011.2.217.7.2.11.67
		-- 1.3.6.1.4.1.2011.2.217.7.2.11.67
		humidity6 OBJECT-TYPE
			SYNTAX Integer32
			MAX-ACCESS read-only
			STATUS current
			DESCRIPTION
				"Description."
			::= { temperatureAndHumidity 67 }

		
--  1.3.6.1.4.1.2011.2.217.7.2.11.68
		-- 1.3.6.1.4.1.2011.2.217.7.2.11.68
		temperature6 OBJECT-TYPE
			SYNTAX Integer32
			MAX-ACCESS read-only
			STATUS current
			DESCRIPTION
				"Description."
			::= { temperatureAndHumidity 68 }

		
--  1.3.6.1.4.1.2011.2.217.7.2.11.69
		-- 1.3.6.1.4.1.2011.2.217.7.2.11.69
		humidity6upLimitValue OBJECT-TYPE
			SYNTAX Integer32
			MAX-ACCESS read-write
			STATUS current
			DESCRIPTION
				"Description."
			::= { temperatureAndHumidity 69 }

		
--  1.3.6.1.4.1.2011.2.217.7.2.11.70
		-- 1.3.6.1.4.1.2011.2.217.7.2.11.70
		humidity6downLimitValue OBJECT-TYPE
			SYNTAX Integer32
			MAX-ACCESS read-write
			STATUS current
			DESCRIPTION
				"Description."
			::= { temperatureAndHumidity 70 }

		
--  1.3.6.1.4.1.2011.2.217.7.2.11.71
		-- 1.3.6.1.4.1.2011.2.217.7.2.11.71
		temperature6upLimitValue OBJECT-TYPE
			SYNTAX Integer32
			MAX-ACCESS read-write
			STATUS current
			DESCRIPTION
				"Description."
			::= { temperatureAndHumidity 71 }

		
--  1.3.6.1.4.1.2011.2.217.7.2.11.72
		-- 1.3.6.1.4.1.2011.2.217.7.2.11.72
		temperature6downLimitValue OBJECT-TYPE
			SYNTAX Integer32
			MAX-ACCESS read-write
			STATUS current
			DESCRIPTION
				"Description."
			::= { temperatureAndHumidity 72 }

		
--  1.3.6.1.4.1.2011.2.217.7.2.11.73
		-- 1.3.6.1.4.1.2011.2.217.7.2.11.73
		humidity6upLimitAlarmEnable OBJECT-TYPE
			SYNTAX Integer32
			MAX-ACCESS read-write
			STATUS current
			DESCRIPTION
				"Description."
			::= { temperatureAndHumidity 73 }

		
--  1.3.6.1.4.1.2011.2.217.7.2.11.74
		-- 1.3.6.1.4.1.2011.2.217.7.2.11.74
		humidity6downLimitAlarmEnable OBJECT-TYPE
			SYNTAX Integer32
			MAX-ACCESS read-write
			STATUS current
			DESCRIPTION
				"Description."
			::= { temperatureAndHumidity 74 }

		
--  1.3.6.1.4.1.2011.2.217.7.2.11.75
		-- 1.3.6.1.4.1.2011.2.217.7.2.11.75
		temperature6upLimitAlarmEnable OBJECT-TYPE
			SYNTAX Integer32
			MAX-ACCESS read-write
			STATUS current
			DESCRIPTION
				"Description."
			::= { temperatureAndHumidity 75 }

		
--  1.3.6.1.4.1.2011.2.217.7.2.11.76
		-- 1.3.6.1.4.1.2011.2.217.7.2.11.76
		temperature6downLimitAlarmEnable OBJECT-TYPE
			SYNTAX Integer32
			MAX-ACCESS read-write
			STATUS current
			DESCRIPTION
				"Description."
			::= { temperatureAndHumidity 76 }

		
--  1.3.6.1.4.1.2011.2.217.7.2.11.77
		-- 1.3.6.1.4.1.2011.2.217.7.2.11.77
		fault6 OBJECT-TYPE
			SYNTAX Integer32
			MAX-ACCESS read-write
			STATUS current
			DESCRIPTION
				"Description."
			::= { temperatureAndHumidity 77 }

--  1.3.6.1.4.1.2011.2.217.7.2.12
		-- 1.3.6.1.4.1.2011.2.217.7.2.12
		temperatureSensor OBJECT IDENTIFIER ::= { hwSensor 12 }
		
		
--  1.3.6.1.4.1.2011.2.217.7.2.13.1
		-- 1.3.6.1.4.1.2011.2.217.7.2.13.1
		temperature1Value OBJECT-TYPE
			SYNTAX Integer32
			MAX-ACCESS read-only
			STATUS current
			DESCRIPTION
				"Description."
			::= { temperatureSensor 1 }	
--  1.3.6.1.4.1.2011.2.217.7.2.13.2
		-- 1.3.6.1.4.1.2011.2.217.7.2.13.2
		temperature1UpLimitValue OBJECT-TYPE
			SYNTAX Integer32
			MAX-ACCESS read-write
			STATUS current
			DESCRIPTION
				"Description."
			::= { temperatureSensor 2 }	
--  1.3.6.1.4.1.2011.2.217.7.2.13.3
		-- 1.3.6.1.4.1.2011.2.217.7.2.13.3
		temperature1DownLimitValue OBJECT-TYPE
			SYNTAX Integer32
			MAX-ACCESS read-write
			STATUS current
			DESCRIPTION
				"Description."
			::= { temperatureSensor 3 }		
--  1.3.6.1.4.1.2011.2.217.7.2.13.4
		-- 1.3.6.1.4.1.2011.2.217.7.2.13.4
		temperature1HighTemperatureAlarmSwitch OBJECT-TYPE
			SYNTAX Integer32
			MAX-ACCESS read-write
			STATUS current
			DESCRIPTION
				"Description."
			::= { temperatureSensor 4 }	
--  1.3.6.1.4.1.2011.2.217.7.2.13.5
		-- 1.3.6.1.4.1.2011.2.217.7.2.13.5
		temperature1LowTemperatureAlarmSwitch OBJECT-TYPE
			SYNTAX Integer32
			MAX-ACCESS read-write
			STATUS current
			DESCRIPTION
				"Description."
			::= { temperatureSensor 5 }	
--  1.3.6.1.4.1.2011.2.217.7.2.13.6
		-- 1.3.6.1.4.1.2011.2.217.7.2.13.6
		temperature1FaultAlarmSwitch OBJECT-TYPE
			SYNTAX Integer32
			MAX-ACCESS read-write
			STATUS current
			DESCRIPTION
				"Description."
			::= { temperatureSensor 6 }		

--  1.3.6.1.4.1.2011.2.217.7.2.13.7
		-- 1.3.6.1.4.1.2011.2.217.7.2.13.7
		temperature2Value OBJECT-TYPE
			SYNTAX Integer32
			MAX-ACCESS read-only
			STATUS current
			DESCRIPTION
				"Description."
			::= { temperatureSensor 7 }	
--  1.3.6.1.4.1.2011.2.217.7.2.13.8
		-- 1.3.6.1.4.1.2011.2.217.7.2.13.8
		temperature2UpLimitValue OBJECT-TYPE
			SYNTAX Integer32
			MAX-ACCESS read-write
			STATUS current
			DESCRIPTION
				"Description."
			::= { temperatureSensor 8 }	
--  1.3.6.1.4.1.2011.2.217.7.2.13.9
		-- 1.3.6.1.4.1.2011.2.217.7.2.13.9
		temperature2DownLimitValue OBJECT-TYPE
			SYNTAX Integer32
			MAX-ACCESS read-write
			STATUS current
			DESCRIPTION
				"Description."
			::= { temperatureSensor 9 }		
--  1.3.6.1.4.1.2011.2.217.7.2.13.10
		-- 1.3.6.1.4.1.2011.2.217.7.2.13.10
		temperature2HighTemperatureAlarmSwitch OBJECT-TYPE
			SYNTAX Integer32
			MAX-ACCESS read-write
			STATUS current
			DESCRIPTION
				"Description."
			::= { temperatureSensor 10}	
--  1.3.6.1.4.1.2011.2.217.7.2.13.11
		-- 1.3.6.1.4.1.2011.2.217.7.2.13.11
		temperature2LowTemperatureAlarmSwitch OBJECT-TYPE
			SYNTAX Integer32
			MAX-ACCESS read-write
			STATUS current
			DESCRIPTION
				"Description."
			::= { temperatureSensor 11}	
--  1.3.6.1.4.1.2011.2.217.7.2.13.12
		-- 1.3.6.1.4.1.2011.2.217.7.2.13.12
		temperature2FaultAlarmSwitch OBJECT-TYPE
			SYNTAX Integer32
			MAX-ACCESS read-write
			STATUS current
			DESCRIPTION
				"Description."
			::= { temperatureSensor 12 }	


--  1.3.6.1.4.1.2011.2.217.7.2.13.13
		-- 1.3.6.1.4.1.2011.2.217.7.2.13.13
		temperature3Value OBJECT-TYPE
			SYNTAX Integer32
			MAX-ACCESS read-only
			STATUS current
			DESCRIPTION
				"Description."
			::= { temperatureSensor 13 }	
--  1.3.6.1.4.1.2011.2.217.7.2.13.14
		-- 1.3.6.1.4.1.2011.2.217.7.2.13.14
		temperature3UpLimitValue OBJECT-TYPE
			SYNTAX Integer32
			MAX-ACCESS read-write
			STATUS current
			DESCRIPTION
				"Description."
			::= { temperatureSensor 14}	
--  1.3.6.1.4.1.2011.2.217.7.2.13.15
		-- 1.3.6.1.4.1.2011.2.217.7.2.13.15
		temperature3DownLimitValue OBJECT-TYPE
			SYNTAX Integer32
			MAX-ACCESS read-write
			STATUS current
			DESCRIPTION
				"Description."
			::= { temperatureSensor 15 }		
--  1.3.6.1.4.1.2011.2.217.7.2.13.16
		-- 1.3.6.1.4.1.2011.2.217.7.2.13.16
		temperature3HighTemperatureAlarmSwitch OBJECT-TYPE
			SYNTAX Integer32
			MAX-ACCESS read-write
			STATUS current
			DESCRIPTION
				"Description."
			::= { temperatureSensor 16}	
--  1.3.6.1.4.1.2011.2.217.7.2.13.17
		-- 1.3.6.1.4.1.2011.2.217.7.2.13.17
		temperature3LowTemperatureAlarmSwitch OBJECT-TYPE
			SYNTAX Integer32
			MAX-ACCESS read-write
			STATUS current
			DESCRIPTION
				"Description."
			::= { temperatureSensor 17}	
--  1.3.6.1.4.1.2011.2.217.7.2.13.18
		-- 1.3.6.1.4.1.2011.2.217.7.2.13.18
		temperature3FaultAlarmSwitch OBJECT-TYPE
			SYNTAX Integer32
			MAX-ACCESS read-write
			STATUS current
			DESCRIPTION
				"Description."
			::= { temperatureSensor 18 }	
			
		
--  1.3.6.1.4.1.2011.2.217.7.2.13
		-- 1.3.6.1.4.1.2011.2.217.7.2.13
		door OBJECT IDENTIFIER ::= { hwSensor 13 }

		
--  1.3.6.1.4.1.2011.2.217.7.2.13.1
		-- 1.3.6.1.4.1.2011.2.217.7.2.13.1
		door0 OBJECT-TYPE
			SYNTAX Integer32
			MAX-ACCESS read-only
			STATUS current
			DESCRIPTION
				"Description."
			::= { door 1 }

		
--  1.3.6.1.4.1.2011.2.217.7.2.13.2
		-- 1.3.6.1.4.1.2011.2.217.7.2.13.2
		door0Enable OBJECT-TYPE
			SYNTAX Integer32
			MAX-ACCESS read-write
			STATUS current
			DESCRIPTION
				"Description."
			::= { door 2 }

		
--  1.3.6.1.4.1.2011.2.217.7.2.13.3
		-- 1.3.6.1.4.1.2011.2.217.7.2.13.3
		door1 OBJECT-TYPE
			SYNTAX Integer32
			MAX-ACCESS read-only
			STATUS current
			DESCRIPTION
				"Description."
			::= { door 3 }

		
--  1.3.6.1.4.1.2011.2.217.7.2.13.4
		-- 1.3.6.1.4.1.2011.2.217.7.2.13.4
		door1Enable OBJECT-TYPE
			SYNTAX Integer32
			MAX-ACCESS read-write
			STATUS current
			DESCRIPTION
				"Description."
			::= { door 4 }

		
--  1.3.6.1.4.1.2011.2.217.7.2.17
		-- 1.3.6.1.4.1.2011.2.217.7.2.17
		alarmStatus OBJECT IDENTIFIER ::= { hwSensor 17 }
		
--  1.3.6.1.4.1.2011.2.217.7.2.17.29
		-- 1.3.6.1.4.1.2011.2.217.7.2.17.29
		proportionalLv1Alarm OBJECT-TYPE
			SYNTAX Integer32
			MAX-ACCESS read-only
			STATUS current
			DESCRIPTION
				"Description."
			::= { alarmStatus 29 }

		
--  1.3.6.1.4.1.2011.2.217.7.2.17.30
		-- 1.3.6.1.4.1.2011.2.217.7.2.17.30
		proportionalLv2Alarm OBJECT-TYPE
			SYNTAX Integer32
			MAX-ACCESS read-only
			STATUS current
			DESCRIPTION
				"Description."
			::= { alarmStatus 30 }

		
--  1.3.6.1.4.1.2011.2.217.7.2.17.50
		-- 1.3.6.1.4.1.2011.2.217.7.2.17.50
		temperatureAndHumidity0faultAlarm OBJECT-TYPE
			SYNTAX Integer32
			MAX-ACCESS read-only
			STATUS current
			DESCRIPTION
				"Description."
			::= { alarmStatus 50 }

		
--  1.3.6.1.4.1.2011.2.217.7.2.17.51
		-- 1.3.6.1.4.1.2011.2.217.7.2.17.51
		temperatureAndHumidity1faultAlarm OBJECT-TYPE
			SYNTAX Integer32
			MAX-ACCESS read-only
			STATUS current
			DESCRIPTION
				"Description."
			::= { alarmStatus 51 }

		
--  1.3.6.1.4.1.2011.2.217.7.2.17.52
		-- 1.3.6.1.4.1.2011.2.217.7.2.17.52
		temperatureAndHumidity2faultAlarm OBJECT-TYPE
			SYNTAX Integer32
			MAX-ACCESS read-only
			STATUS current
			DESCRIPTION
				"Description."
			::= { alarmStatus 52 }

		
--  1.3.6.1.4.1.2011.2.217.7.2.17.53
		-- 1.3.6.1.4.1.2011.2.217.7.2.17.53
		temperatureAndHumidity3faultAlarm OBJECT-TYPE
			SYNTAX Integer32
			MAX-ACCESS read-only
			STATUS current
			DESCRIPTION
				"Description."
			::= { alarmStatus 53 }

--  1.3.6.1.4.1.2011.2.217.7.2.17.74
		-- 1.3.6.1.4.1.2011.2.217.7.2.17.74
		temperatureAndHumidity4faultAlarm OBJECT-TYPE
			SYNTAX Integer32
			MAX-ACCESS read-only
			STATUS current
			DESCRIPTION
				"Description."
			::= { alarmStatus 74 }

--  1.3.6.1.4.1.2011.2.217.7.2.17.75
		-- 1.3.6.1.4.1.2011.2.217.7.2.17.75
		temperatureAndHumidity5faultAlarm OBJECT-TYPE
			SYNTAX Integer32
			MAX-ACCESS read-only
			STATUS current
			DESCRIPTION
				"Description."
			::= { alarmStatus 75 }	

--  1.3.6.1.4.1.2011.2.217.7.2.17.76
		-- 1.3.6.1.4.1.2011.2.217.7.2.17.76
		temperatureAndHumidity6faultAlarm OBJECT-TYPE
			SYNTAX Integer32
			MAX-ACCESS read-only
			STATUS current
			DESCRIPTION
				"Description."
			::= { alarmStatus 76 }	
			
--  1.3.6.1.4.1.2011.2.217.7.2.17.77
		-- 1.3.6.1.4.1.2011.2.217.7.2.17.77
		temperature1ConnectStatus OBJECT-TYPE
			SYNTAX Integer32
			MAX-ACCESS read-only
			STATUS current
			DESCRIPTION
				"Description."
			::= { alarmStatus 77 }		
--  1.3.6.1.4.1.2011.2.217.7.2.17.78
		-- 1.3.6.1.4.1.2011.2.217.7.2.17.78
		temperature2ConnectStatus OBJECT-TYPE
			SYNTAX Integer32
			MAX-ACCESS read-only
			STATUS current
			DESCRIPTION
				"Description."
			::= { alarmStatus 78 }	
--  1.3.6.1.4.1.2011.2.217.7.2.17.79
		-- 1.3.6.1.4.1.2011.2.217.7.2.17.79
		temperature3ConnectStatus OBJECT-TYPE
			SYNTAX Integer32
			MAX-ACCESS read-only
			STATUS current
			DESCRIPTION
				"Description."
			::= { alarmStatus 79 }				
		
		-- 1.3.6.1.4.1.2011.2.217.7.4
		hwTrapargs OBJECT IDENTIFIER ::= { hwLcs 4 }

		
		-- 1.3.6.1.4.1.2011.2.217.7.4.2
		hwTrapIpTable OBJECT IDENTIFIER ::= { hwTrapargs 2 }

		
		-- 1.3.6.1.4.1.2011.2.217.7.4.2.1
		trapIp OBJECT IDENTIFIER ::= { hwTrapIpTable 1 }
		
		-- 1.3.6.1.4.1.2011.2.217.7.4.2.1.2
		getSetTrapIp OBJECT IDENTIFIER ::= { trapIp 2 }

		
		-- 1.3.6.1.4.1.2011.2.217.7.4.2.1.2.1
		trapIp1 OBJECT-TYPE
			SYNTAX OCTET STRING
			MAX-ACCESS read-write
			STATUS current
			DESCRIPTION
				"Description."
			::= { getSetTrapIp 1 }

		
		-- 1.3.6.1.4.1.2011.2.217.7.4.2.1.2.2
		trapIp2 OBJECT-TYPE
			SYNTAX OCTET STRING
			MAX-ACCESS read-write
			STATUS current
			DESCRIPTION
				"Description."
			::= { getSetTrapIp 2 }

		
		-- 1.3.6.1.4.1.2011.2.217.7.4.2.1.2.3
		trapIp3 OBJECT-TYPE
			SYNTAX OCTET STRING
			MAX-ACCESS read-write
			STATUS current
			DESCRIPTION
				"Description."
			::= { getSetTrapIp 3 }

		
		-- 1.3.6.1.4.1.2011.2.217.7.4.2.1.3
		delTrapIp OBJECT IDENTIFIER ::= { trapIp 3 }

		
		-- 1.3.6.1.4.1.2011.2.217.7.4.2.1.3.1
		delIp1 OBJECT-TYPE
			SYNTAX Integer32
			MAX-ACCESS read-write
			STATUS current
			DESCRIPTION
				"Description."
			::= { delTrapIp 1 }

		
		-- 1.3.6.1.4.1.2011.2.217.7.4.2.1.3.2
		delIp2 OBJECT-TYPE
			SYNTAX Integer32
			MAX-ACCESS read-write
			STATUS current
			DESCRIPTION
				"Description."
			::= { delTrapIp 2 }

		
		-- 1.3.6.1.4.1.2011.2.217.7.4.2.1.3.3
		delIp3 OBJECT-TYPE
			SYNTAX Integer32
			MAX-ACCESS read-write
			STATUS current
			DESCRIPTION
				"Description."
			::= { delTrapIp 3 }


		hwTrapAlarmList OBJECT IDENTIFIER ::= { hwLcs 3 }
		
		photoelectricLiquidLevelSensor-0-Alarm NOTIFICATION-TYPE
			STATUS  current
			DESCRIPTION
               ""
			::= { hwTrapAlarmList 11 }
			
		photoelectricLiquidLevelSensor-0-AlarmCleared NOTIFICATION-TYPE
			STATUS  current
			DESCRIPTION
               ""
			::= { hwTrapAlarmList 12 }
			
		photoelectricLiquidLevelSensor-1-Alarm NOTIFICATION-TYPE
			STATUS  current
			DESCRIPTION
               ""
			::= { hwTrapAlarmList 13 }
			
		photoelectricLiquidLevelSensor-1-AlarmCleared NOTIFICATION-TYPE
			STATUS  current
			DESCRIPTION
               ""
			::= { hwTrapAlarmList 14 }
			
		photoelectricLiquidLevelSensor-2-Alarm NOTIFICATION-TYPE
			STATUS  current
			DESCRIPTION
               ""
			::= { hwTrapAlarmList 15 }
			
		photoelectricLiquidLevelSensor-2-AlarmCleared NOTIFICATION-TYPE
			STATUS  current
			DESCRIPTION
               ""
			::= { hwTrapAlarmList 16 }	
			
		photoelectricLiquidLevelSensor-3-Alarm NOTIFICATION-TYPE
			STATUS  current
			DESCRIPTION
               ""
			::= { hwTrapAlarmList 17 }
			
		photoelectricLiquidLevelSensor-3-AlarmCleared NOTIFICATION-TYPE
			STATUS  current
			DESCRIPTION
               ""
			::= { hwTrapAlarmList 18 }					
			
		floatTypeLiquidLevelSensor-0-Alarm NOTIFICATION-TYPE
			STATUS  current
			DESCRIPTION
               ""
			::= { hwTrapAlarmList 31 }
			
		floatTypeLiquidLevelSensor-0-AlarmCleared NOTIFICATION-TYPE
			STATUS  current
			DESCRIPTION
               ""
			::= { hwTrapAlarmList 32 }		

		floatTypeLiquidLevelSensor-1-Alarm NOTIFICATION-TYPE
			STATUS  current
			DESCRIPTION
               ""
			::= { hwTrapAlarmList 33 }
			
		floatTypeLiquidLevelSensor-1-AlarmCleared NOTIFICATION-TYPE
			STATUS  current
			DESCRIPTION
               ""
			::= { hwTrapAlarmList 34 }		

		floatTypeLiquidLevelSensor-2-Alarm NOTIFICATION-TYPE
			STATUS  current
			DESCRIPTION
               ""
			::= { hwTrapAlarmList 35 }
			
		floatTypeLiquidLevelSensor-2-AlarmCleared NOTIFICATION-TYPE
			STATUS  current
			DESCRIPTION
               ""
			::= { hwTrapAlarmList 36 }	

		floatTypeLiquidLevelSensor-3-Alarm NOTIFICATION-TYPE
			STATUS  current
			DESCRIPTION
               ""
			::= { hwTrapAlarmList 37 }
			
		floatTypeLiquidLevelSensor-3-AlarmCleared NOTIFICATION-TYPE
			STATUS  current
			DESCRIPTION
               ""
			::= { hwTrapAlarmList 38 }	


		liquidLeakageSensor-3-Alarm NOTIFICATION-TYPE
			STATUS  current
			DESCRIPTION
               ""
			::= { hwTrapAlarmList 53 }
			
		liquidLeakageSensor-3-AlarmCleared NOTIFICATION-TYPE
			STATUS  current
			DESCRIPTION
               ""
			::= { hwTrapAlarmList 54 }		

		actuatorProportionalValve-1-FaultAlarm NOTIFICATION-TYPE
			STATUS  current
			DESCRIPTION
               ""
			::= { hwTrapAlarmList 59 }
			
		actuatorProportionalValve-1-FaultAlarmCleared NOTIFICATION-TYPE
			STATUS  current
			DESCRIPTION
               ""
			::= { hwTrapAlarmList 60 }		
		actuatorProportionalValve-2-FaultAlarm NOTIFICATION-TYPE
			STATUS  current
			DESCRIPTION
               ""
			::= { hwTrapAlarmList 61 }
			
		actuatorProportionalValve-2-FaultAlarmCleared NOTIFICATION-TYPE
			STATUS  current
			DESCRIPTION
               ""
			::= { hwTrapAlarmList 62 }	

		temperatureAndHumiditySensor-0-FaultAlarm NOTIFICATION-TYPE
			STATUS  current
			DESCRIPTION
               ""
			::= { hwTrapAlarmList 119 }
			
		temperatureAndHumiditySensor-0-FaultAlarmCleared NOTIFICATION-TYPE
			STATUS  current
			DESCRIPTION
               ""
			::= { hwTrapAlarmList 120 }		

		temperatureAndHumiditySensor-1-FaultAlarm NOTIFICATION-TYPE
			STATUS  current
			DESCRIPTION
               ""
			::= { hwTrapAlarmList 121 }
			
		temperatureAndHumiditySensor-1-FaultAlarmCleared NOTIFICATION-TYPE
			STATUS  current
			DESCRIPTION
               ""
			::= { hwTrapAlarmList 122 }			

		temperatureAndHumiditySensor-2-FaultAlarm NOTIFICATION-TYPE
			STATUS  current
			DESCRIPTION
               ""
			::= { hwTrapAlarmList 123 }
			
		temperatureAndHumiditySensor-2-FaultAlarmCleared NOTIFICATION-TYPE
			STATUS  current
			DESCRIPTION
               ""
			::= { hwTrapAlarmList 124 }		

		temperatureAndHumiditySensor-3-FaultAlarm NOTIFICATION-TYPE
			STATUS  current
			DESCRIPTION
               ""
			::= { hwTrapAlarmList 125 }
			
		temperatureAndHumiditySensor-3-FaultAlarmCleared NOTIFICATION-TYPE
			STATUS  current
			DESCRIPTION
               ""
			::= { hwTrapAlarmList 126 }		

		temperatureAndHumiditySensor-4-FaultAlarm NOTIFICATION-TYPE
			STATUS  current
			DESCRIPTION
               ""
			::= { hwTrapAlarmList 127 }
			
		temperatureAndHumiditySensor-4-FaultAlarmCleared NOTIFICATION-TYPE
			STATUS  current
			DESCRIPTION
               ""
			::= { hwTrapAlarmList 128 }		

		temperatureAndHumiditySensor-5-FaultAlarm NOTIFICATION-TYPE
			STATUS  current
			DESCRIPTION
               ""
			::= { hwTrapAlarmList 129 }
			
		temperatureAndHumiditySensor-5-FaultAlarmCleared NOTIFICATION-TYPE
			STATUS  current
			DESCRIPTION
               ""
			::= { hwTrapAlarmList 130 }	
			
		temperatureAndHumiditySensor-6-FaultAlarm NOTIFICATION-TYPE
			STATUS  current
			DESCRIPTION
               ""
			::= { hwTrapAlarmList 247 }		

		temperatureAndHumiditySensor-6-FaultAlarmCleared NOTIFICATION-TYPE
			STATUS  current
			DESCRIPTION
               ""
			::= { hwTrapAlarmList 248 }		

		accessControl-0-Alarm NOTIFICATION-TYPE
			STATUS  current
			DESCRIPTION
               ""
			::= { hwTrapAlarmList 165 }
			
		accessControl-0-AlarmCleared NOTIFICATION-TYPE
			STATUS  current
			DESCRIPTION
               ""
			::= { hwTrapAlarmList 166 }		

		accessControl-1-Alarm NOTIFICATION-TYPE
			STATUS  current
			DESCRIPTION
               ""
			::= { hwTrapAlarmList 167 }
			
		accessControl-1-AlarmCleared NOTIFICATION-TYPE
			STATUS  current
			DESCRIPTION
               ""
			::= { hwTrapAlarmList 168 }		


		fileDownloadSucceeded NOTIFICATION-TYPE
			STATUS  current
			DESCRIPTION
               ""
			::= { hwTrapAlarmList 195 }
			
		fileDownloadFailed NOTIFICATION-TYPE
			STATUS  current
			DESCRIPTION
               ""
			::= { hwTrapAlarmList 196 }		


		temperatureAndHumiditySensor-0-OverTemperatureAlarm NOTIFICATION-TYPE
			STATUS  current
			DESCRIPTION
               ""
			::= { hwTrapAlarmList 199 }
			
		temperatureAndHumiditySensor-0-OverTemperatureAlarmCleared NOTIFICATION-TYPE
			STATUS  current
			DESCRIPTION
               ""
			::= { hwTrapAlarmList 200 }				
			
		temperatureAndHumiditySensor-0-LowTemperatureAlarm NOTIFICATION-TYPE
			STATUS  current
			DESCRIPTION
               ""
			::= { hwTrapAlarmList 201 }
			
		temperatureAndHumiditySensor-0-LowTemperatureAlarmCleared NOTIFICATION-TYPE
			STATUS  current
			DESCRIPTION
               ""
			::= { hwTrapAlarmList 202 }		


		temperatureAndHumiditySensor-0-OverHumidityAlarm NOTIFICATION-TYPE
			STATUS  current
			DESCRIPTION
               ""
			::= { hwTrapAlarmList 203 }
			
		temperatureAndHumiditySensor-0-OverHumidityAlarmCleared NOTIFICATION-TYPE
			STATUS  current
			DESCRIPTION
               ""
			::= { hwTrapAlarmList 204 }				
			
		temperatureAndHumiditySensor-0-LowHumidityAlarm NOTIFICATION-TYPE
			STATUS  current
			DESCRIPTION
               ""
			::= { hwTrapAlarmList 205 }
			
		temperatureAndHumiditySensor-0-LowHumidityAlarmCleared NOTIFICATION-TYPE
			STATUS  current
			DESCRIPTION
               ""
			::= { hwTrapAlarmList 206 }	


		temperatureAndHumiditySensor-1-OverTemperatureAlarm NOTIFICATION-TYPE
			STATUS  current
			DESCRIPTION
               ""
			::= { hwTrapAlarmList 207 }
			
		temperatureAndHumiditySensor-1-OverTemperatureAlarmCleared NOTIFICATION-TYPE
			STATUS  current
			DESCRIPTION
               ""
			::= { hwTrapAlarmList 208 }				
			
		temperatureAndHumiditySensor-1-LowTemperatureAlarm NOTIFICATION-TYPE
			STATUS  current
			DESCRIPTION
               ""
			::= { hwTrapAlarmList 209 }
			
		temperatureAndHumiditySensor-1-LowTemperatureAlarmCleared NOTIFICATION-TYPE
			STATUS  current
			DESCRIPTION
               ""
			::= { hwTrapAlarmList 210 }		

		temperatureAndHumiditySensor-1-OverHumidityAlarm NOTIFICATION-TYPE
			STATUS  current
			DESCRIPTION
               ""
			::= { hwTrapAlarmList 211 }
			
		temperatureAndHumiditySensor-1-OverHumidityAlarmCleared NOTIFICATION-TYPE
			STATUS  current
			DESCRIPTION
               ""
			::= { hwTrapAlarmList 212 }				
			
		temperatureAndHumiditySensor-1-LowHumidityAlarm NOTIFICATION-TYPE
			STATUS  current
			DESCRIPTION
               ""
			::= { hwTrapAlarmList 213 }
			
		temperatureAndHumiditySensor-1-LowHumidityAlarmCleared NOTIFICATION-TYPE
			STATUS  current
			DESCRIPTION
               ""
			::= { hwTrapAlarmList 214 }	



		temperatureAndHumiditySensor-2-OverTemperatureAlarm NOTIFICATION-TYPE
			STATUS  current
			DESCRIPTION
               ""
			::= { hwTrapAlarmList 215 }
			
		temperatureAndHumiditySensor-2-OverTemperatureAlarmCleared NOTIFICATION-TYPE
			STATUS  current
			DESCRIPTION
               ""
			::= { hwTrapAlarmList 216 }				
			
		temperatureAndHumiditySensor-2-LowTemperatureAlarm NOTIFICATION-TYPE
			STATUS  current
			DESCRIPTION
               ""
			::= { hwTrapAlarmList 217 }
			
		temperatureAndHumiditySensor-2-LowTemperatureAlarmCleared NOTIFICATION-TYPE
			STATUS  current
			DESCRIPTION
               ""
			::= { hwTrapAlarmList 218 }		


		temperatureAndHumiditySensor-2-OverHumidityAlarm NOTIFICATION-TYPE
			STATUS  current
			DESCRIPTION
               ""
			::= { hwTrapAlarmList 219 }
			
		temperatureAndHumiditySensor-2-OverHumidityAlarmCleared NOTIFICATION-TYPE
			STATUS  current
			DESCRIPTION
               ""
			::= { hwTrapAlarmList 220 }				
			
		temperatureAndHumiditySensor-2-LowHumidityAlarm NOTIFICATION-TYPE
			STATUS  current
			DESCRIPTION
               ""
			::= { hwTrapAlarmList 221 }
			
		temperatureAndHumiditySensor-2-LowHumidityAlarmCleared NOTIFICATION-TYPE
			STATUS  current
			DESCRIPTION
               ""
			::= { hwTrapAlarmList 222 }		


		temperatureAndHumiditySensor-3-OverTemperatureAlarm NOTIFICATION-TYPE
			STATUS  current
			DESCRIPTION
               ""
			::= { hwTrapAlarmList 223 }
			
		temperatureAndHumiditySensor-3-OverTemperatureAlarmCleared NOTIFICATION-TYPE
			STATUS  current
			DESCRIPTION
               ""
			::= { hwTrapAlarmList 224 }				
			
		temperatureAndHumiditySensor-3-LowTemperatureAlarm NOTIFICATION-TYPE
			STATUS  current
			DESCRIPTION
               ""
			::= { hwTrapAlarmList 225 }
			
		temperatureAndHumiditySensor-3-LowTemperatureAlarmCleared NOTIFICATION-TYPE
			STATUS  current
			DESCRIPTION
               ""
			::= { hwTrapAlarmList 226 }		


		temperatureAndHumiditySensor-3-OverHumidityAlarm NOTIFICATION-TYPE
			STATUS  current
			DESCRIPTION
               ""
			::= { hwTrapAlarmList 227 }
			
		temperatureAndHumiditySensor-3-OverHumidityAlarmCleared NOTIFICATION-TYPE
			STATUS  current
			DESCRIPTION
               ""
			::= { hwTrapAlarmList 228 }				
			
		temperatureAndHumiditySensor-3-LowHumidityAlarm NOTIFICATION-TYPE
			STATUS  current
			DESCRIPTION
               ""
			::= { hwTrapAlarmList 229 }
			
		temperatureAndHumiditySensor-3-LowHumidityAlarmCleared NOTIFICATION-TYPE
			STATUS  current
			DESCRIPTION
               ""
			::= { hwTrapAlarmList 230 }		



		temperatureAndHumiditySensor-4-OverTemperatureAlarm NOTIFICATION-TYPE
			STATUS  current
			DESCRIPTION
               ""
			::= { hwTrapAlarmList 231 }
			
		temperatureAndHumiditySensor-4-OverTemperatureAlarmCleared NOTIFICATION-TYPE
			STATUS  current
			DESCRIPTION
               ""
			::= { hwTrapAlarmList 232 }				
			
		temperatureAndHumiditySensor-4-LowTemperatureAlarm NOTIFICATION-TYPE
			STATUS  current
			DESCRIPTION
               ""
			::= { hwTrapAlarmList 233 }
			
		temperatureAndHumiditySensor-4-LowTemperatureAlarmCleared NOTIFICATION-TYPE
			STATUS  current
			DESCRIPTION
               ""
			::= { hwTrapAlarmList 234 }		


		temperatureAndHumiditySensor-4-OverHumidityAlarm NOTIFICATION-TYPE
			STATUS  current
			DESCRIPTION
               ""
			::= { hwTrapAlarmList 235 }
			
		temperatureAndHumiditySensor-4-OverHumidityAlarmCleared NOTIFICATION-TYPE
			STATUS  current
			DESCRIPTION
               ""
			::= { hwTrapAlarmList 236 }				
			
		temperatureAndHumiditySensor-4-LowHumidityAlarm NOTIFICATION-TYPE
			STATUS  current
			DESCRIPTION
               ""
			::= { hwTrapAlarmList 237 }
			
		temperatureAndHumiditySensor-4-LowHumidityAlarmCleared NOTIFICATION-TYPE
			STATUS  current
			DESCRIPTION
               ""
			::= { hwTrapAlarmList 238 }	



		temperatureAndHumiditySensor-5-OverTemperatureAlarm NOTIFICATION-TYPE
			STATUS  current
			DESCRIPTION
               ""
			::= { hwTrapAlarmList 239 }
			
		temperatureAndHumiditySensor-5-OverTemperatureAlarmCleared NOTIFICATION-TYPE
			STATUS  current
			DESCRIPTION
               ""
			::= { hwTrapAlarmList 240 }				
			
		temperatureAndHumiditySensor-5-LowTemperatureAlarm NOTIFICATION-TYPE
			STATUS  current
			DESCRIPTION
               ""
			::= { hwTrapAlarmList 241 }
			
		temperatureAndHumiditySensor-5-LowTemperatureAlarmCleared NOTIFICATION-TYPE
			STATUS  current
			DESCRIPTION
               ""
			::= { hwTrapAlarmList 242 }		


		temperatureAndHumiditySensor-5-OverHumidityAlarm NOTIFICATION-TYPE
			STATUS  current
			DESCRIPTION
               ""
			::= { hwTrapAlarmList 243 }
			
		temperatureAndHumiditySensor-5-OverHumidityAlarmCleared NOTIFICATION-TYPE
			STATUS  current
			DESCRIPTION
               ""
			::= { hwTrapAlarmList 244 }				
			
		temperatureAndHumiditySensor-5-LowHumidityAlarm NOTIFICATION-TYPE
			STATUS  current
			DESCRIPTION
               ""
			::= { hwTrapAlarmList 245 }
			
		temperatureAndHumiditySensor-5-LowHumidityAlarmCleared NOTIFICATION-TYPE
			STATUS  current
			DESCRIPTION
               ""
			::= { hwTrapAlarmList 246 }		


		temperatureAndHumiditySensor-6-OverTemperatureAlarm NOTIFICATION-TYPE
			STATUS  current
			DESCRIPTION
               ""
			::= { hwTrapAlarmList 249 }
			
		temperatureAndHumiditySensor-6-OverTemperatureAlarmCleared NOTIFICATION-TYPE
			STATUS  current
			DESCRIPTION
               ""
			::= { hwTrapAlarmList 250 }				
			
		temperatureAndHumiditySensor-6-LowTemperatureAlarm NOTIFICATION-TYPE
			STATUS  current
			DESCRIPTION
               ""
			::= { hwTrapAlarmList 251 }
			
		temperatureAndHumiditySensor-6-LowTemperatureAlarmCleared NOTIFICATION-TYPE
			STATUS  current
			DESCRIPTION
               ""
			::= { hwTrapAlarmList 252 }		


		temperatureAndHumiditySensor-6-OverHumidityAlarm NOTIFICATION-TYPE
			STATUS  current
			DESCRIPTION
               ""
			::= { hwTrapAlarmList 253 }
			
		temperatureAndHumiditySensor-6-OverHumidityAlarmCleared NOTIFICATION-TYPE
			STATUS  current
			DESCRIPTION
               ""
			::= { hwTrapAlarmList 254 }				
			
		temperatureAndHumiditySensor-6-LowHumidityAlarm NOTIFICATION-TYPE
			STATUS  current
			DESCRIPTION
               ""
			::= { hwTrapAlarmList 255 }
			
		temperatureAndHumiditySensor-6-LowHumidityAlarmCleared NOTIFICATION-TYPE
			STATUS  current
			DESCRIPTION
               ""
			::= { hwTrapAlarmList 256 }			
	
	END

--
-- CCU-ZYT-MIB.my
--
