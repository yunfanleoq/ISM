--
-- S03B-MIB.my
-- MIB generated by MG-SOFT Visual MIB Builder Version 6.0  Build 88
-- Tuesday, March 05, 2019 at 11:19:34
--

--  S03B-MIB.my
-- MIB generated by MG-SOFT Visual MIB Builder Version 6.0  Build 88
-- Saturday, January 26, 2019 at 18:06:21
-- 

	S03B-MIB DEFINITIONS ::= BEGIN
 
		IMPORTS
			enterprises,MODULE-IDENTITY, OBJECT-TYPE, Integer32, Unsigned32,
				Gauge32, Counter32, Counter64, IpAddress, mib-2
             FROM SNMPv2-SMI
			DisplayString
					FROM SNMPv2-TC;
--  1.3.6.1.4.1.2011
-- January 24, 2019 at 09:55 GMT
		-- 1.3.6.1.4.1.2011
		zyt MODULE-IDENTITY 
			LAST-UPDATED "201901240955Z"		-- January 24, 2019 at 09:55 GMT
			ORGANIZATION 
				"ZYT"
			CONTACT-INFO 
				"hexinjun@robot-zyt.com"
			DESCRIPTION 
				"Description."
			::= { enterprises 7944 }

		
	
--
-- Node definitions
--
	
--  Node definitions
-- 
-- 1.3.6.1.4.1.2011.2
		-- 1.3.6.1.4.1.2011.2
		products OBJECT IDENTIFIER ::= { zyt 7999 }
		
--  1.3.6.1.4.1.2011.2.217.7.1.1
		-- 1.3.6.1.4.1.2011.2.217.7.1.1
		snmpBoardParameter OBJECT IDENTIFIER ::= { products 2 }

		
--  1.3.6.1.4.1.2011.2.217.7.1.1.1
		-- 1.3.6.1.4.1.2011.2.217.7.1.1.1
		softwareVersion OBJECT-TYPE
			SYNTAX DisplayString
			MAX-ACCESS read-only
			STATUS current
			DESCRIPTION
				"Description."
			::= { snmpBoardParameter 3 } 
			
-- 1.3.6.1.4.1.7944.7999.2.8
		host-IP-Address OBJECT-TYPE
			SYNTAX IpAddress
			MAX-ACCESS read-write
			STATUS current
			DESCRIPTION
				""
			::= { snmpBoardParameter 8 }
			
		-- 1.3.6.1.4.1.7944.7999.2.9
		host-netMASK OBJECT-TYPE
			SYNTAX IpAddress
			MAX-ACCESS read-write
			STATUS current
			DESCRIPTION
				""
			::= { snmpBoardParameter 9 }
			
		-- 1.3.6.1.4.1.7944.7999.2.10
		host-netGateWay OBJECT-TYPE
			SYNTAX IpAddress
			MAX-ACCESS read-write
			STATUS current
			DESCRIPTION
				""
			::= { snmpBoardParameter 10 }
			
		-- 1.3.6.1.4.1.7944.7999.2.11
		host-netMAC OBJECT-TYPE
			SYNTAX DisplayString
			MAX-ACCESS read-write
			STATUS current
			DESCRIPTION
				""
			::= { snmpBoardParameter 11 }
			
		-- 1.3.6.1.4.1.7944.7999.1.4
		snmp-agent-port OBJECT-TYPE
			SYNTAX INTEGER
			MAX-ACCESS read-write
			STATUS current
			DESCRIPTION
				""
			::= { snmpBoardParameter 12 }
			
		-- 1.3.6.1.4.1.7944.7999.1.5
		snmp-trap-port OBJECT-TYPE
			SYNTAX INTEGER
			MAX-ACCESS read-write
			STATUS current
			DESCRIPTION
				""
			::= { snmpBoardParameter 13 }
			
		-- 1.3.6.1.4.1.7944.7999.1.14
		snmp-trap-ipaddress OBJECT-TYPE
			SYNTAX IpAddress
			MAX-ACCESS read-write
			STATUS current
			DESCRIPTION
				""
			::= { snmpBoardParameter 14 }	
			
					-- 1.3.6.1.4.1.7944.7999.1.14
		snmp-protocol-enable OBJECT-TYPE
			SYNTAX INTEGER
			MAX-ACCESS read-write
			STATUS current
			DESCRIPTION
				""
			::= { snmpBoardParameter 15 }	
			

--  1.3.6.1.4.1.2011.2.217.7.1.2
		-- 1.3.6.1.4.1.2011.2.217.7.1.2
		fcs-Parameter OBJECT IDENTIFIER ::= { products 1 }


-- 1.3.6.1.4.1.7944.7999.1.14
		fcs-software-version OBJECT-TYPE
			SYNTAX INTEGER
			MAX-ACCESS read-only
			STATUS current
			DESCRIPTION
				""
			::= { fcs-Parameter 1 }

		fcs-restart-times OBJECT-TYPE
			SYNTAX INTEGER
			MAX-ACCESS read-only
			STATUS current
			DESCRIPTION
				""
			::= { fcs-Parameter 2 }	
			
		fcs-restart OBJECT-TYPE
			SYNTAX INTEGER
			MAX-ACCESS read-write
			STATUS current
			DESCRIPTION
				""
			::= { fcs-Parameter 3 }	
			
		fcs-factory-default OBJECT-TYPE
			SYNTAX INTEGER
			MAX-ACCESS read-write
			STATUS current
			DESCRIPTION
				""
			::= { fcs-Parameter 4 }	
			
		fcs-systemdate-year OBJECT-TYPE
			SYNTAX INTEGER
			MAX-ACCESS read-write
			STATUS current
			DESCRIPTION
				""
			::= { fcs-Parameter 5 }	
		fcs-systemdate-month OBJECT-TYPE
			SYNTAX INTEGER
			MAX-ACCESS read-write
			STATUS current
			DESCRIPTION
				""
			::= { fcs-Parameter 6 }	

		fcs-systemdate-day OBJECT-TYPE
			SYNTAX INTEGER
			MAX-ACCESS read-write
			STATUS current
			DESCRIPTION
				""
			::= { fcs-Parameter 7 }	

		fcs-systemdate-hour OBJECT-TYPE
			SYNTAX INTEGER
			MAX-ACCESS read-write
			STATUS current
			DESCRIPTION
				""
			::= { fcs-Parameter 8 }	

		fcs-systemdate-minute OBJECT-TYPE
			SYNTAX INTEGER
			MAX-ACCESS read-write
			STATUS current
			DESCRIPTION
				""
			::= { fcs-Parameter 9 }				
	
		fcs-control-heater OBJECT-TYPE
			SYNTAX INTEGER
			MAX-ACCESS read-write
			STATUS current
			DESCRIPTION
				""
			::= { fcs-Parameter 10 }		
--  1.3.6.1.4.1.2011.2.217.7.1.2.1
		-- 1.3.6.1.4.1.2011.2.217.7.1.2.1
		inside-temperature OBJECT-TYPE
			SYNTAX DisplayString
			MAX-ACCESS read-only
			STATUS current
			DESCRIPTION
				""
			::= { fcs-Parameter 11 }		

--  1.3.6.1.4.1.2011.2.217.7.1.2.2
		-- 1.3.6.1.4.1.2011.2.217.7.1.2.2
		inside-humidity OBJECT-TYPE
			SYNTAX DisplayString
			MAX-ACCESS read-only
			STATUS current
			DESCRIPTION
				""
			::= { fcs-Parameter 12 }			
		
--  1.3.6.1.4.1.2011.2.217.7.1.2.3
		-- 1.3.6.1.4.1.2011.2.217.7.1.2.3
		outside-temperature  OBJECT-TYPE
			SYNTAX DisplayString
			MAX-ACCESS read-only
			STATUS current
			DESCRIPTION
				""
			::= { fcs-Parameter 13 }
		infrared-alarm  OBJECT-TYPE
			SYNTAX INTEGER
			MAX-ACCESS read-only
			STATUS current
			DESCRIPTION
				""
			::= { fcs-Parameter 14 }
		water-alarm  OBJECT-TYPE
			SYNTAX INTEGER
			MAX-ACCESS read-only
			STATUS current
			DESCRIPTION
				""
			::= { fcs-Parameter 15 }
		smoke-alarm  OBJECT-TYPE
			SYNTAX INTEGER
			MAX-ACCESS read-only
			STATUS current
			DESCRIPTION
				""
			::= { fcs-Parameter 16 }
		door-alarm  OBJECT-TYPE
			SYNTAX INTEGER
			MAX-ACCESS read-only
			STATUS current
			DESCRIPTION
				""
			::= { fcs-Parameter 17 }			
		battery-voltage  OBJECT-TYPE
			SYNTAX DisplayString
			MAX-ACCESS read-only
			STATUS current
			DESCRIPTION
				""
			::= { fcs-Parameter 18}	
		inside-temperature-status  OBJECT-TYPE
			SYNTAX INTEGER
			MAX-ACCESS read-only
			STATUS current
			DESCRIPTION
				""
			::= { fcs-Parameter 19 }
		outside-temperature-status  OBJECT-TYPE
			SYNTAX INTEGER
			MAX-ACCESS read-only
			STATUS current
			DESCRIPTION
				""
			::= { fcs-Parameter 20 }	
		inside-humidity-status  OBJECT-TYPE
			SYNTAX INTEGER
			MAX-ACCESS read-only
			STATUS current
			DESCRIPTION
				""
			::= { fcs-Parameter 21 }

		control-ac1  OBJECT-TYPE
			SYNTAX INTEGER
			MAX-ACCESS read-write
			STATUS current
			DESCRIPTION
				""
			::= { fcs-Parameter 22 }	
		control-ac2  OBJECT-TYPE
			SYNTAX INTEGER
			MAX-ACCESS read-write
			STATUS current
			DESCRIPTION
				""
			::= { fcs-Parameter 23 }

		control-fan  OBJECT-TYPE
			SYNTAX INTEGER
			MAX-ACCESS read-write
			STATUS current
			DESCRIPTION
				""
			::= { fcs-Parameter 24 }	

		ac1-fault  OBJECT-TYPE
			SYNTAX INTEGER
			MAX-ACCESS read-only
			STATUS current
			DESCRIPTION
				""
			::= { fcs-Parameter 25 }
		ac2-fault  OBJECT-TYPE
			SYNTAX INTEGER
			MAX-ACCESS read-only
			STATUS current
			DESCRIPTION
				""
			::= { fcs-Parameter 26 }

		fan-fault  OBJECT-TYPE
			SYNTAX INTEGER
			MAX-ACCESS read-only
			STATUS current
			DESCRIPTION
				""
			::= { fcs-Parameter 27 }	

		ac1-feed  OBJECT-TYPE
			SYNTAX INTEGER
			MAX-ACCESS read-only
			STATUS current
			DESCRIPTION
				""
			::= { fcs-Parameter 28 }	

		ac2-feed  OBJECT-TYPE
			SYNTAX INTEGER
			MAX-ACCESS read-only
			STATUS current
			DESCRIPTION
				""
			::= { fcs-Parameter 29 }	

		filter-alarm  OBJECT-TYPE
			SYNTAX INTEGER
			MAX-ACCESS read-only
			STATUS current
			DESCRIPTION
				""
			::= { fcs-Parameter 30 }	

		fire-alarm  OBJECT-TYPE
			SYNTAX INTEGER
			MAX-ACCESS read-only
			STATUS current
			DESCRIPTION
				""
			::= { fcs-Parameter 31 }	

		fan-run-total-time  OBJECT-TYPE
			SYNTAX INTEGER
			MAX-ACCESS read-only
			STATUS current
			DESCRIPTION
				""
			::= { fcs-Parameter 32 }	
		ac1-run-total-time  OBJECT-TYPE
			SYNTAX INTEGER
			MAX-ACCESS read-only
			STATUS current
			DESCRIPTION
				""
			::= { fcs-Parameter 33 }	
		ac2-run-total-time  OBJECT-TYPE
			SYNTAX INTEGER
			MAX-ACCESS read-only
			STATUS current
			DESCRIPTION
				""
			::= { fcs-Parameter 34 }		

		heater-run-total-time  OBJECT-TYPE
			SYNTAX INTEGER
			MAX-ACCESS read-only
			STATUS current
			DESCRIPTION
				""
			::= { fcs-Parameter 35 }

		low-temperature-run-fan-time  OBJECT-TYPE
			SYNTAX INTEGER
			MAX-ACCESS read-write
			STATUS current
			DESCRIPTION
				""
			::= { fcs-Parameter 36 }

		humidity-higth-close-fan-up-limit  OBJECT-TYPE
			SYNTAX INTEGER
			MAX-ACCESS read-write
			STATUS current
			DESCRIPTION
				""
			::= { fcs-Parameter 37 }
		fan-fault-temperature-difference  OBJECT-TYPE
			SYNTAX INTEGER
			MAX-ACCESS read-write
			STATUS current
			DESCRIPTION
				""
			::= { fcs-Parameter 38 }
			
		fan-fault-check-time  OBJECT-TYPE
			SYNTAX INTEGER
			MAX-ACCESS read-write
			STATUS current
			DESCRIPTION
				""
			::= { fcs-Parameter 39 }
		ac-fault-temperature  OBJECT-TYPE
			SYNTAX INTEGER
			MAX-ACCESS read-write
			STATUS current
			DESCRIPTION
				""
			::= { fcs-Parameter 40 }	
		ac-fault-check-time  OBJECT-TYPE
			SYNTAX INTEGER
			MAX-ACCESS read-write
			STATUS current
			DESCRIPTION
				""
			::= { fcs-Parameter 41 }	
		ac-switch-time  OBJECT-TYPE
			SYNTAX INTEGER
			MAX-ACCESS read-write
			STATUS current
			DESCRIPTION
				""
			::= { fcs-Parameter 42 }
		inside-temperature-up-limit  OBJECT-TYPE
			SYNTAX  DisplayString
			MAX-ACCESS read-write
			STATUS current
			DESCRIPTION
				""
			::= { fcs-Parameter 43 }
		inside-temperature-down-limit  OBJECT-TYPE
			SYNTAX  DisplayString
			MAX-ACCESS read-write
			STATUS current
			DESCRIPTION
				""
			::= { fcs-Parameter 44 }
		inside-humidity-up-limit  OBJECT-TYPE
			SYNTAX  DisplayString
			MAX-ACCESS read-write
			STATUS current
			DESCRIPTION
				""
			::= { fcs-Parameter 45 }	
		inside-humidity-dwon-limit  OBJECT-TYPE
			SYNTAX  DisplayString
			MAX-ACCESS read-write
			STATUS current
			DESCRIPTION
				""
			::= { fcs-Parameter 46 }	
		outside-temperature-down-limit  OBJECT-TYPE
			SYNTAX  DisplayString
			MAX-ACCESS read-write
			STATUS current
			DESCRIPTION
				""
			::= { fcs-Parameter 47 }				
		outside-temperature-up-limit  OBJECT-TYPE
			SYNTAX  DisplayString
			MAX-ACCESS read-write
			STATUS current
			DESCRIPTION
				""
			::= { fcs-Parameter 48 }

		ac-min-run-time  OBJECT-TYPE
			SYNTAX INTEGER
			MAX-ACCESS read-write
			STATUS current
			DESCRIPTION
				""
			::= { fcs-Parameter 49 }
		fcs-working-mode  OBJECT-TYPE
			SYNTAX INTEGER
			MAX-ACCESS read-write
			STATUS current
			DESCRIPTION
				""
			::= { fcs-Parameter 50 }

		ac-delay-start-tpye  OBJECT-TYPE
			SYNTAX INTEGER
			MAX-ACCESS read-write
			STATUS current
			DESCRIPTION
				""
			::= { fcs-Parameter 51 }	

		clear-smoke  OBJECT-TYPE
			SYNTAX INTEGER
			MAX-ACCESS read-write
			STATUS current
			DESCRIPTION
				""
			::= { fcs-Parameter 52 }	

		clear-all-alarms  OBJECT-TYPE
			SYNTAX INTEGER
			MAX-ACCESS read-write
			STATUS current
			DESCRIPTION
				""
			::= { fcs-Parameter 53 }

		fan-start-temperature  OBJECT-TYPE
			SYNTAX DisplayString
			MAX-ACCESS read-write
			STATUS current
			DESCRIPTION
				""
			::= { fcs-Parameter 54 }	
		ac-start-temperature  OBJECT-TYPE
			SYNTAX DisplayString
			MAX-ACCESS read-write
			STATUS current
			DESCRIPTION
				""
			::= { fcs-Parameter 55 }	
		urgency-mode-temperature  OBJECT-TYPE
			SYNTAX DisplayString
			MAX-ACCESS read-write
			STATUS current
			DESCRIPTION
				""
			::= { fcs-Parameter 56 }	
		temperature-high-alarm-limit-value  OBJECT-TYPE
			SYNTAX DisplayString
			MAX-ACCESS read-write
			STATUS current
			DESCRIPTION
				""
			::= { fcs-Parameter 57 }	

		humidity-alarm-enable  OBJECT-TYPE
			SYNTAX INTEGER
			MAX-ACCESS read-write
			STATUS current
			DESCRIPTION
				""
			::= { fcs-Parameter 58 }	
		heater-start-temperature  OBJECT-TYPE
			SYNTAX DisplayString
			MAX-ACCESS read-write
			STATUS current
			DESCRIPTION
				""
			::= { fcs-Parameter 59 }
		heater-stop-temperature  OBJECT-TYPE
			SYNTAX DisplayString
			MAX-ACCESS read-write
			STATUS current
			DESCRIPTION
				""
			::= { fcs-Parameter 60 }
		fan-min-start-time  OBJECT-TYPE
			SYNTAX INTEGER
			MAX-ACCESS read-write
			STATUS current
			DESCRIPTION
				""
			::= { fcs-Parameter 61 }	
		fan-low-speed  OBJECT-TYPE
			SYNTAX INTEGER
			MAX-ACCESS read-write
			STATUS current
			DESCRIPTION
				""
			::= { fcs-Parameter 62 }	
		fan-middle-speed  OBJECT-TYPE
			SYNTAX INTEGER
			MAX-ACCESS read-write
			STATUS current
			DESCRIPTION
				""
			::= { fcs-Parameter 63 }
		fan-high-speed  OBJECT-TYPE
			SYNTAX INTEGER
			MAX-ACCESS read-write
			STATUS current
			DESCRIPTION
				""
			::= { fcs-Parameter 64 }

		fan-feed-speed  OBJECT-TYPE
			SYNTAX INTEGER
			MAX-ACCESS read-write
			STATUS current
			DESCRIPTION
				""
			::= { fcs-Parameter 65 }

		fan-control-speed  OBJECT-TYPE
			SYNTAX INTEGER
			MAX-ACCESS read-write
			STATUS current
			DESCRIPTION
				""
			::= { fcs-Parameter 66 }

		pass-check-self  OBJECT-TYPE
			SYNTAX INTEGER
			MAX-ACCESS read-write
			STATUS current
			DESCRIPTION
				""
			::= { fcs-Parameter 67 }

		clear-all-history  OBJECT-TYPE
			SYNTAX INTEGER
			MAX-ACCESS read-write
			STATUS current
			DESCRIPTION
				""
			::= { fcs-Parameter 68 }	

		battery-down-limit-value  OBJECT-TYPE
			SYNTAX DisplayString
			MAX-ACCESS read-write
			STATUS current
			DESCRIPTION
				""
			::= { fcs-Parameter 69 }	

		battery-low-close-fan-enable  OBJECT-TYPE
			SYNTAX INTEGER
			MAX-ACCESS read-write
			STATUS current
			DESCRIPTION
				""
			::= { fcs-Parameter 70 }	
			
		battery-low-alarm-difference  OBJECT-TYPE
			SYNTAX INTEGER
			MAX-ACCESS read-write
			STATUS current
			DESCRIPTION
				""
			::= { fcs-Parameter 71 }		
		mix-enable-switch  OBJECT-TYPE
			SYNTAX INTEGER
			MAX-ACCESS read-write
			STATUS current
			DESCRIPTION
				""
			::= { fcs-Parameter 72 }	
		mix-angle  OBJECT-TYPE
			SYNTAX INTEGER
			MAX-ACCESS read-write
			STATUS current
			DESCRIPTION
				""
			::= { fcs-Parameter 73 }	

		mix-temperature  OBJECT-TYPE
			SYNTAX DisplayString
			MAX-ACCESS read-write
			STATUS current
			DESCRIPTION
				""
			::= { fcs-Parameter 74 }				
			
	END

--
-- S03B-MIB.my
--
