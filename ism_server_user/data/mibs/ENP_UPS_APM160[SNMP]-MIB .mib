------------------------------------------------------------
-- Vertiv
-- ITEI MIB
------------------------------------------------------------

DCS-MIB DEFINITIONS ::= BEGIN

IMPORTS
	MODULE-IDENTITY, OBJECT-TYPE, NOTIFICATION-TYPE,Integer32, Counter32, enterprises		FROM SNMPv2-SMI
	TEXTUAL-CONVENTION, DisplayString, DateAndTime											FROM SNMPv2-TC;
	
------------------------------------------------------------
-- Node definitions
------------------------------------------------------------
dcs MODULE-IDENTITY
	LAST-UPDATED "201808160000Z"
	ORGANIZATION "Vertiv"
	CONTACT-INFO "vertivc.service@vertivco.com"
	Revision     "201808160000Z"
	DESCRIPTION  "Vertiv device MIB"

	::= { enp 3 }
	


enp OBJECT IDENTIFIER ::= { enterprises 13400 }


------------------------------------------------------------
-- Textual conventions
------------------------------------------------------------

AlarmSeverity ::= TEXTUAL-CONVENTION
	STATUS current
	DESCRIPTION "
		The severity of the alarm. One of
		(1) informational
		(2) warning
		(3) critical"
	SYNTAX INTEGER {
		informational(1),
		warning(2),
		critical(3) }
		
AlarmStatusChange ::= TEXTUAL-CONVENTION
	STATUS current
	DESCRIPTION "
		Indicates 'activated' (0) or 'deactivated' (1) alarm events."
	SYNTAX INTEGER {
		activated(0),
		deactivated(1) }
		
		
------------------------------------------------------------
-- System Info{ 13400.3.1 }
------------------------------------------------------------

systemInfo OBJECT IDENTIFIER ::=  { dcs 1 }

systemLoaction OBJECT-TYPE
		SYNTAX 			DisplayString
		MAX-ACCESS 		read-only
		STATUS 			current
		DESCRIPTION 	"Where is this Uint"
		::= 			{ systemInfo 1 }

systemEquipNum OBJECT-TYPE
		SYNTAX 			Integer32
		MAX-ACCESS 		read-only
		STATUS 			current
		DESCRIPTION 	"System Equipment Number"
		::=				{ systemInfo 2 }
		
systemEquipListTable OBJECT-TYPE
		SYNTAX 			SEQUENCE OF SystemEquipListEntry
		MAX-ACCESS 		not-accessible
		STATUS 			current
		DESCRIPTION 	"System Equipment List Table"
		::= 			{ systemInfo 3 }
	
systemEquipListEntry OBJECT-TYPE
		SYNTAX 			SystemEquipListEntry
		MAX-ACCESS 		not-accessible
		STATUS 			current
		DESCRIPTION 	"System Equipment List Entry"
		INDEX 			{ systemEquipListIndex }
		::= 			{ systemEquipListTable 1 }

SystemEquipListEntry ::= SEQUENCE {
		systemEquipListIndex 		Integer32,
		systemEquipTypeName			DisplayString,
		systemEquipID				Integer32,
		systemEquipTypeID	 		Integer32}
	
systemEquipListIndex OBJECT-TYPE
		SYNTAX 			Integer32(1..64)
		MAX-ACCESS 		read-only
		STATUS 			current
		DESCRIPTION 	"System Equipment List Index"
		::=				{ systemEquipListEntry 1 }
		
systemEquipTypeName OBJECT-TYPE
		SYNTAX 			DisplayString
		MAX-ACCESS 		read-only
		STATUS 			current
		DESCRIPTION 	"System Equipment Type Name"
		::= 			{ systemEquipListEntry 2 }
		
systemEquipID OBJECT-TYPE
		SYNTAX 			Integer32
		MAX-ACCESS 		read-only
		STATUS 			current
		DESCRIPTION 	"System Equipment ID"
		::= 			{ systemEquipListEntry 3 }

systemEquipTypeID OBJECT-TYPE
		SYNTAX 			Integer32
		MAX-ACCESS 		read-only
		STATUS 			current
		DESCRIPTION 	"System Equipment Type ID"
		::= 			{ systemEquipListEntry 4 }


------------------------------------------------------------
-- Ups { 13400.3.4 }
------------------------------------------------------------
ups OBJECT IDENTIFIER ::=  { dcs 4 }


------------------------------------------------------------
-- Apm160snmp { 13400.3.4.4100 }
------------------------------------------------------------
ups-Apm160snmp OBJECT IDENTIFIER ::= { ups 4100 }
upsApm160snmpTable OBJECT-TYPE
		SYNTAX			SEQUENCE OF UpsApm160snmpEntry
		MAX-ACCESS		not-accessible
		STATUS			current
		DESCRIPTION	"upsApm160snmpTable"
		::=			{ ups-Apm160snmp 1 }
upsApm160snmpEntry OBJECT-TYPE
		SYNTAX			UpsApm160snmpEntry
		MAX-ACCESS		not-accessible
		STATUS			current
		DESCRIPTION		"upsApm160snmpEntry"
		INDEX			{ upsApm160snmpIndex }
		::=				{ upsApm160snmpTable 1 }
UpsApm160snmpEntry ::= SEQUENCE {
		upsApm160snmpIndex					Integer32,
		upsApm160snmp_2_systemOutputAcitvePowerA					Integer32,
		upsApm160snmp_3_systemOutputAcitvePowerB					Integer32,
		upsApm160snmp_4_systemOutputAcitvePowerC					Integer32,
		upsApm160snmp_5_systemOutputAppPowerA					Integer32,
		upsApm160snmp_6_systemOutputAppPowerB					Integer32,
		upsApm160snmp_7_systemOutputAppPowerC					Integer32,
		upsApm160snmp_8_systemOutputReactivePowerA					Integer32,
		upsApm160snmp_9_systemOutputReactivePowerB					Integer32,
		upsApm160snmp_10_systemOutputReactivePowerC					Integer32,
		upsApm160snmp_11_environmentTemperature					Integer32,
		upsApm160snmp_12_requitsiteModules					Integer32,
		upsApm160snmp_13_redundantModules					Integer32,
		upsApm160snmp_14_unitGrantCapacity					Integer32,
		upsApm160snmp_15_unitCapacity					Integer32,
		upsApm160snmp_16_ModuleinputPhaseVoltageA					Integer32,
		upsApm160snmp_17_ModuleinputPhaseVoltageB					Integer32,
		upsApm160snmp_18_ModuleinputPhaseVoltageC					Integer32,
		upsApm160snmp_19_ModuleinputLineVoltageA					Integer32,
		upsApm160snmp_20_ModuleinputLineVoltageB					Integer32,
		upsApm160snmp_21_ModuleinputLineVoltageC					Integer32,
		upsApm160snmp_22_ModuleinputCurrentA					Integer32,
		upsApm160snmp_23_ModuleinputCurrentB					Integer32,
		upsApm160snmp_24_ModuleinputCurrentC					Integer32,
		upsApm160snmp_25_ModuleinputFrequency					Integer32,
		upsApm160snmp_26_ModuleinputPowerFactorA					Integer32,
		upsApm160snmp_27_ModuleinputPowerFactorB					Integer32,
		upsApm160snmp_28_ModuleinputPowerFactorC					Integer32,
		upsApm160snmp_29_ModulebatteryVoltage					Integer32,
		upsApm160snmp_30_ModuleinputActivePowerA					Integer32,
		upsApm160snmp_31_ModuleinputActivePowerB					Integer32,
		upsApm160snmp_32_ModuleinputActivePowerC					Integer32,
		upsApm160snmp_33_ModuleinputAppPowerA					Integer32,
		upsApm160snmp_34_ModuleinputAppPowerB					Integer32,
		upsApm160snmp_35_ModuleinputAppPowerC					Integer32,
		upsApm160snmp_36_ModuleinputEnergyA					Integer32,
		upsApm160snmp_37_ModuleinputEnergyB					Integer32,
		upsApm160snmp_38_ModuleinputEnergyC					Integer32,
		upsApm160snmp_39_ModuleoutputVoltageA					Integer32,
		upsApm160snmp_40_ModuleoutputVoltageB					Integer32,
		upsApm160snmp_41_ModuleoutputVoltageC					Integer32,
		upsApm160snmp_42_ModuleoutputLineVoltageAB					Integer32,
		upsApm160snmp_43_ModuleoutputLineVoltageBC					Integer32,
		upsApm160snmp_44_ModuleoutputLineVoltageCA					Integer32,
		upsApm160snmp_45_ModuleoutputCurrentA					Integer32,
		upsApm160snmp_46_ModuleoutputCurrentB					Integer32,
		upsApm160snmp_47_ModuleoutputCurrentC					Integer32,
		upsApm160snmp_48_ModuleoutputFrequency					Integer32,
		upsApm160snmp_49_ModuleoutputPowerFactorA					Integer32,
		upsApm160snmp_50_ModuleoutputPowerFactorB					Integer32,
		upsApm160snmp_51_ModuleoutputPowerFactorC					Integer32,
		upsApm160snmp_52_ModuleoutputAcitvePowerA					Integer32,
		upsApm160snmp_53_ModuleoutputAcitvePowerB					Integer32,
		upsApm160snmp_54_ModuleoutputAcitvePowerC					Integer32,
		upsApm160snmp_55_ModuleoutputReactivePowerA					Integer32,
		upsApm160snmp_56_ModuleoutputReactivePowerB					Integer32,
		upsApm160snmp_57_ModuleoutputReactivePowerC					Integer32,
		upsApm160snmp_58_ModuleoutputAppPowerA					Integer32,
		upsApm160snmp_59_ModuleoutputAppPowerB					Integer32,
		upsApm160snmp_60_ModuleoutputAppPowerC					Integer32,
		upsApm160snmp_61_ModuleoutputLoadA					Integer32,
		upsApm160snmp_62_ModuleoutputLoadB					Integer32,
		upsApm160snmp_63_ModuleoutputLoadC					Integer32,
		upsApm160snmp_64_ModuleoutputCrestFactorA					Integer32,
		upsApm160snmp_65_ModuleoutputCrestFactorB					Integer32,
		upsApm160snmp_66_ModuleoutputCrestFactorC					Integer32,
		upsApm160snmp_67_ModulebypassVoltageA					Integer32,
		upsApm160snmp_68_ModulebypassVoltageB					Integer32,
		upsApm160snmp_69_ModulebypassVoltageC					Integer32,
		upsApm160snmp_70_ModulebypassLineVoltageAB					Integer32,
		upsApm160snmp_71_ModulebypassLineVoltageBC					Integer32,
		upsApm160snmp_72_ModulebypassLineVoltageCA					Integer32,
		upsApm160snmp_73_ModulebypassFrequency					Integer32,
		upsApm160snmp_74_ModulebatteryRemainsTime					Integer32,
		upsApm160snmp_75_ModulebatteryPositiveVoltage					Integer32,
		upsApm160snmp_76_ModulebatteryPositiveCurrent					Integer32,
		upsApm160snmp_77_ModulebatteryNegativeVoltage					Integer32,
		upsApm160snmp_78_ModulebatteryNegativeCurrent					Integer32,
		upsApm160snmp_79_ModulebatteryAgingRate					Integer32,
		upsApm160snmp_80_ModulebatteryTemperature					Integer32,
		upsApm160snmp_81_Module1inputPhaseVoltageA					Integer32,
		upsApm160snmp_82_Module1inputPhaseVoltageB					Integer32,
		upsApm160snmp_83_Module1inputPhaseVoltageC					Integer32,
		upsApm160snmp_84_Module1inputLineVoltageA					Integer32,
		upsApm160snmp_85_Module1inputLineVoltageB					Integer32,
		upsApm160snmp_86_Module1inputLineVoltageC					Integer32,
		upsApm160snmp_87_Module1inputCurrentA					Integer32,
		upsApm160snmp_88_Module1inputCurrentB					Integer32,
		upsApm160snmp_89_Module1inputCurrentC					Integer32,
		upsApm160snmp_90_Module1inputFrequency					Integer32,
		upsApm160snmp_91_Module1inputPowerFactorA					Integer32,
		upsApm160snmp_92_Module1inputPowerFactorB					Integer32,
		upsApm160snmp_93_Module1inputPowerFactorC					Integer32,
		upsApm160snmp_94_Module1batteryVoltage					Integer32,
		upsApm160snmp_95_Module1inputActivePowerA					Integer32,
		upsApm160snmp_96_Module1inputActivePowerB					Integer32,
		upsApm160snmp_97_Module1inputActivePowerC					Integer32,
		upsApm160snmp_98_Module1inputAppPowerA					Integer32,
		upsApm160snmp_99_Module1inputAppPowerB					Integer32,
		upsApm160snmp_100_Module1inputAppPowerC					Integer32,
		upsApm160snmp_101_Module1inputEnergyA					Integer32,
		upsApm160snmp_102_Module1inputEnergyB					Integer32,
		upsApm160snmp_103_Module1inputEnergyC					Integer32,
		upsApm160snmp_104_Module1outputVoltageA					Integer32,
		upsApm160snmp_105_Module1outputVoltageB					Integer32,
		upsApm160snmp_106_Module1outputVoltageC					Integer32,
		upsApm160snmp_107_Module1outputLineVoltageAB					Integer32,
		upsApm160snmp_108_Module1outputLineVoltageBC					Integer32,
		upsApm160snmp_109_Module1outputLineVoltageCA					Integer32,
		upsApm160snmp_110_Module1outputCurrentA					Integer32,
		upsApm160snmp_111_Module1outputCurrentB					Integer32,
		upsApm160snmp_112_Module1outputCurrentC					Integer32,
		upsApm160snmp_113_Module1outputFrequency					Integer32,
		upsApm160snmp_114_Module1outputPowerFactorA					Integer32,
		upsApm160snmp_115_Module1outputPowerFactorB					Integer32,
		upsApm160snmp_116_Module1outputPowerFactorC					Integer32,
		upsApm160snmp_117_Module1outputAcitvePowerA					Integer32,
		upsApm160snmp_118_Module1outputAcitvePowerB					Integer32,
		upsApm160snmp_119_Module1outputAcitvePowerC					Integer32,
		upsApm160snmp_120_Module1outputReactivePowerA					Integer32,
		upsApm160snmp_121_Module1outputReactivePowerB					Integer32,
		upsApm160snmp_122_Module1outputReactivePowerC					Integer32,
		upsApm160snmp_123_Module1outputAppPowerA					Integer32,
		upsApm160snmp_124_Module1outputAppPowerB					Integer32,
		upsApm160snmp_125_Module1outputAppPowerC					Integer32,
		upsApm160snmp_126_Module1outputLoadA					Integer32,
		upsApm160snmp_127_Module1outputLoadB					Integer32,
		upsApm160snmp_128_Module1outputLoadC					Integer32,
		upsApm160snmp_129_Module1outputCrestFactorA					Integer32,
		upsApm160snmp_130_Module1outputCrestFactorB					Integer32,
		upsApm160snmp_131_Module1outputCrestFactorC					Integer32,
		upsApm160snmp_132_Module1bypassVoltageA					Integer32,
		upsApm160snmp_133_Module1bypassVoltageB					Integer32,
		upsApm160snmp_134_Module1bypassVoltageC					Integer32,
		upsApm160snmp_135_Module1bypassLineVoltageAB					Integer32,
		upsApm160snmp_136_Module1bypassLineVoltageBC					Integer32,
		upsApm160snmp_137_Module1bypassLineVoltageCA					Integer32,
		upsApm160snmp_138_Module1bypassFrequency					Integer32,
		upsApm160snmp_139_Module1batteryRemainsTime					Integer32,
		upsApm160snmp_140_Module1batteryPositiveVoltage					Integer32,
		upsApm160snmp_141_Module1batteryPositiveCurrent					Integer32,
		upsApm160snmp_142_Module1batteryNegativeVoltage					Integer32,
		upsApm160snmp_143_Module1batteryNegativeCurrent					Integer32,
		upsApm160snmp_144_Module1batteryAgingRate					Integer32,
		upsApm160snmp_145_Module1batteryTemperature					Integer32,
		upsApm160snmp_146_Module2inputPhaseVoltageA					Integer32,
		upsApm160snmp_147_Module2inputPhaseVoltageB					Integer32,
		upsApm160snmp_148_Module2inputPhaseVoltageC					Integer32,
		upsApm160snmp_149_Module2inputLineVoltageA					Integer32,
		upsApm160snmp_150_Module2inputLineVoltageB					Integer32,
		upsApm160snmp_151_Module2inputLineVoltageC					Integer32,
		upsApm160snmp_152_Module2inputCurrentA					Integer32,
		upsApm160snmp_153_Module2inputCurrentB					Integer32,
		upsApm160snmp_154_Module2inputCurrentC					Integer32,
		upsApm160snmp_155_Module2inputFrequency					Integer32,
		upsApm160snmp_156_Module2inputPowerFactorA					Integer32,
		upsApm160snmp_157_Module2inputPowerFactorB					Integer32,
		upsApm160snmp_158_Module2inputPowerFactorC					Integer32,
		upsApm160snmp_159_Module2batteryVoltage					Integer32,
		upsApm160snmp_160_Module2inputActivePowerA					Integer32,
		upsApm160snmp_161_Module2inputActivePowerB					Integer32,
		upsApm160snmp_162_Module2inputActivePowerC					Integer32,
		upsApm160snmp_163_Module2inputAppPowerA					Integer32,
		upsApm160snmp_164_Module2inputAppPowerB					Integer32,
		upsApm160snmp_165_Module2inputAppPowerC					Integer32,
		upsApm160snmp_166_Module2inputEnergyA					Integer32,
		upsApm160snmp_167_Module2inputEnergyB					Integer32,
		upsApm160snmp_168_Module2inputEnergyC					Integer32,
		upsApm160snmp_169_Module2outputVoltageA					Integer32,
		upsApm160snmp_170_Module2outputVoltageB					Integer32,
		upsApm160snmp_171_Module2outputVoltageC					Integer32,
		upsApm160snmp_172_Module2outputLineVoltageAB					Integer32,
		upsApm160snmp_173_Module2outputLineVoltageBC					Integer32,
		upsApm160snmp_174_Module2outputLineVoltageCA					Integer32,
		upsApm160snmp_175_Module2outputCurrentA					Integer32,
		upsApm160snmp_176_Module2outputCurrentB					Integer32,
		upsApm160snmp_177_Module2outputCurrentC					Integer32,
		upsApm160snmp_178_Module2outputFrequency					Integer32,
		upsApm160snmp_179_Module2outputPowerFactorA					Integer32,
		upsApm160snmp_180_Module2outputPowerFactorB					Integer32,
		upsApm160snmp_181_Module2outputPowerFactorC					Integer32,
		upsApm160snmp_182_Module2outputAcitvePowerA					Integer32,
		upsApm160snmp_183_Module2outputAcitvePowerB					Integer32,
		upsApm160snmp_184_Module2outputAcitvePowerC					Integer32,
		upsApm160snmp_185_Module2outputReactivePowerA					Integer32,
		upsApm160snmp_186_Module2outputReactivePowerB					Integer32,
		upsApm160snmp_187_Module2outputReactivePowerC					Integer32,
		upsApm160snmp_188_Module2outputAppPowerA					Integer32,
		upsApm160snmp_189_Module2outputAppPowerB					Integer32,
		upsApm160snmp_190_Module2outputAppPowerC					Integer32,
		upsApm160snmp_191_Module2outputLoadA					Integer32,
		upsApm160snmp_192_Module2outputLoadB					Integer32,
		upsApm160snmp_193_Module2outputLoadC					Integer32,
		upsApm160snmp_194_Module2outputCrestFactorA					Integer32,
		upsApm160snmp_195_Module2outputCrestFactorB					Integer32,
		upsApm160snmp_196_Module2outputCrestFactorC					Integer32,
		upsApm160snmp_197_Module2bypassVoltageA					Integer32,
		upsApm160snmp_198_Module2bypassVoltageB					Integer32,
		upsApm160snmp_199_Module2bypassVoltageC					Integer32,
		upsApm160snmp_200_Module2bypassLineVoltageAB					Integer32,
		upsApm160snmp_201_Module2bypassLineVoltageBC					Integer32,
		upsApm160snmp_202_Module2bypassLineVoltageCA					Integer32,
		upsApm160snmp_203_Module2bypassFrequency					Integer32,
		upsApm160snmp_204_Module2batteryRemainsTime					Integer32,
		upsApm160snmp_205_Module2batteryPositiveVoltage					Integer32,
		upsApm160snmp_206_Module2batteryPositiveCurrent					Integer32,
		upsApm160snmp_207_Module2batteryNegativeVoltage					Integer32,
		upsApm160snmp_208_Module2batteryNegativeCurrent					Integer32,
		upsApm160snmp_209_Module2batteryAgingRate					Integer32,
		upsApm160snmp_210_Module2batteryTemperature					Integer32,
		upsApm160snmp_211_Module3inputPhaseVoltageA					Integer32,
		upsApm160snmp_212_Module3inputPhaseVoltageB					Integer32,
		upsApm160snmp_213_Module3inputPhaseVoltageC					Integer32,
		upsApm160snmp_214_Module3inputLineVoltageA					Integer32,
		upsApm160snmp_215_Module3inputLineVoltageB					Integer32,
		upsApm160snmp_216_Module3inputLineVoltageC					Integer32,
		upsApm160snmp_217_Module3inputCurrentA					Integer32,
		upsApm160snmp_218_Module3inputCurrentB					Integer32,
		upsApm160snmp_219_Module3inputCurrentC					Integer32,
		upsApm160snmp_220_Module3inputFrequency					Integer32,
		upsApm160snmp_221_Module3inputPowerFactorA					Integer32,
		upsApm160snmp_222_Module3inputPowerFactorB					Integer32,
		upsApm160snmp_223_Module3inputPowerFactorC					Integer32,
		upsApm160snmp_224_Module3batteryVoltage					Integer32,
		upsApm160snmp_225_Module3inputActivePowerA					Integer32,
		upsApm160snmp_226_Module3inputActivePowerB					Integer32,
		upsApm160snmp_227_Module3inputActivePowerC					Integer32,
		upsApm160snmp_228_Module3inputAppPowerA					Integer32,
		upsApm160snmp_229_Module3inputAppPowerB					Integer32,
		upsApm160snmp_230_Module3inputAppPowerC					Integer32,
		upsApm160snmp_231_Module3inputEnergyA					Integer32,
		upsApm160snmp_232_Module3inputEnergyB					Integer32,
		upsApm160snmp_233_Module3inputEnergyC					Integer32,
		upsApm160snmp_234_Module3outputVoltageA					Integer32,
		upsApm160snmp_235_Module3outputVoltageB					Integer32,
		upsApm160snmp_236_Module3outputVoltageC					Integer32,
		upsApm160snmp_237_Module3outputLineVoltageAB					Integer32,
		upsApm160snmp_238_Module3outputLineVoltageBC					Integer32,
		upsApm160snmp_239_Module3outputLineVoltageCA					Integer32,
		upsApm160snmp_240_Module3outputCurrentA					Integer32,
		upsApm160snmp_241_Module3outputCurrentB					Integer32,
		upsApm160snmp_242_Module3outputCurrentC					Integer32,
		upsApm160snmp_243_Module3outputFrequency					Integer32,
		upsApm160snmp_244_Module3outputPowerFactorA					Integer32,
		upsApm160snmp_245_Module3outputPowerFactorB					Integer32,
		upsApm160snmp_246_Module3outputPowerFactorC					Integer32,
		upsApm160snmp_247_Module3outputAcitvePowerA					Integer32,
		upsApm160snmp_248_Module3outputAcitvePowerB					Integer32,
		upsApm160snmp_249_Module3outputAcitvePowerC					Integer32,
		upsApm160snmp_250_Module3outputReactivePowerA					Integer32,
		upsApm160snmp_251_Module3outputReactivePowerB					Integer32,
		upsApm160snmp_252_Module3outputReactivePowerC					Integer32,
		upsApm160snmp_253_Module3outputAppPowerA					Integer32,
		upsApm160snmp_254_Module3outputAppPowerB					Integer32,
		upsApm160snmp_255_Module3outputAppPowerC					Integer32,
		upsApm160snmp_256_Module3outputLoadA					Integer32,
		upsApm160snmp_257_Module3outputLoadB					Integer32,
		upsApm160snmp_258_Module3outputLoadC					Integer32,
		upsApm160snmp_259_Module3outputCrestFactorA					Integer32,
		upsApm160snmp_260_Module3outputCrestFactorB					Integer32,
		upsApm160snmp_261_Module3outputCrestFactorC					Integer32,
		upsApm160snmp_262_Module3bypassVoltageA					Integer32,
		upsApm160snmp_263_Module3bypassVoltageB					Integer32,
		upsApm160snmp_264_Module3bypassVoltageC					Integer32,
		upsApm160snmp_265_Module3bypassLineVoltageAB					Integer32,
		upsApm160snmp_266_Module3bypassLineVoltageBC					Integer32,
		upsApm160snmp_267_Module3bypassLineVoltageCA					Integer32,
		upsApm160snmp_268_Module3bypassFrequency					Integer32,
		upsApm160snmp_269_Module3batteryRemainsTime					Integer32,
		upsApm160snmp_270_Module3batteryPositiveVoltage					Integer32,
		upsApm160snmp_271_Module3batteryPositiveCurrent					Integer32,
		upsApm160snmp_272_Module3batteryNegativeVoltage					Integer32,
		upsApm160snmp_273_Module3batteryNegativeCurrent					Integer32,
		upsApm160snmp_274_Module3batteryAgingRate					Integer32,
		upsApm160snmp_275_Module3batteryTemperature					Integer32,
		upsApm160snmp_276_Module4inputPhaseVoltageA					Integer32,
		upsApm160snmp_277_Module4inputPhaseVoltageB					Integer32,
		upsApm160snmp_278_Module4inputPhaseVoltageC					Integer32,
		upsApm160snmp_279_Module4inputLineVoltageA					Integer32,
		upsApm160snmp_280_Module4inputLineVoltageB					Integer32,
		upsApm160snmp_281_Module4inputLineVoltageC					Integer32,
		upsApm160snmp_282_Module4inputCurrentA					Integer32,
		upsApm160snmp_283_Module4inputCurrentB					Integer32,
		upsApm160snmp_284_Module4inputCurrentC					Integer32,
		upsApm160snmp_285_Module4inputFrequency					Integer32,
		upsApm160snmp_286_Module4inputPowerFactorA					Integer32,
		upsApm160snmp_287_Module4inputPowerFactorB					Integer32,
		upsApm160snmp_288_Module4inputPowerFactorC					Integer32,
		upsApm160snmp_289_Module4batteryVoltage					Integer32,
		upsApm160snmp_290_Module4inputActivePowerA					Integer32,
		upsApm160snmp_291_Module4inputActivePowerB					Integer32,
		upsApm160snmp_292_Module4inputActivePowerC					Integer32,
		upsApm160snmp_293_Module4inputAppPowerA					Integer32,
		upsApm160snmp_294_Module4inputAppPowerB					Integer32,
		upsApm160snmp_295_Module4inputAppPowerC					Integer32,
		upsApm160snmp_296_Module4inputEnergyA					Integer32,
		upsApm160snmp_297_Module4inputEnergyB					Integer32,
		upsApm160snmp_298_Module4inputEnergyC					Integer32,
		upsApm160snmp_299_Module4outputVoltageA					Integer32,
		upsApm160snmp_300_Module4outputVoltageB					Integer32,
		upsApm160snmp_301_Module4outputVoltageC					Integer32,
		upsApm160snmp_302_Module4outputLineVoltageAB					Integer32,
		upsApm160snmp_303_Module4outputLineVoltageBC					Integer32,
		upsApm160snmp_304_Module4outputLineVoltageCA					Integer32,
		upsApm160snmp_305_Module4outputCurrentA					Integer32,
		upsApm160snmp_306_Module4outputCurrentB					Integer32,
		upsApm160snmp_307_Module4outputCurrentC					Integer32,
		upsApm160snmp_308_Module4outputFrequency					Integer32,
		upsApm160snmp_309_Module4outputPowerFactorA					Integer32,
		upsApm160snmp_310_Module4outputPowerFactorB					Integer32,
		upsApm160snmp_311_Module4outputPowerFactorC					Integer32,
		upsApm160snmp_312_Module4outputAcitvePowerA					Integer32,
		upsApm160snmp_313_Module4outputAcitvePowerB					Integer32,
		upsApm160snmp_314_Module4outputAcitvePowerC					Integer32,
		upsApm160snmp_315_Module4outputReactivePowerA					Integer32,
		upsApm160snmp_316_Module4outputReactivePowerB					Integer32,
		upsApm160snmp_317_Module4outputReactivePowerC					Integer32,
		upsApm160snmp_318_Module4outputAppPowerA					Integer32,
		upsApm160snmp_319_Module4outputAppPowerB					Integer32,
		upsApm160snmp_320_Module4outputAppPowerC					Integer32,
		upsApm160snmp_321_Module4outputLoadA					Integer32,
		upsApm160snmp_322_Module4outputLoadB					Integer32,
		upsApm160snmp_323_Module4outputLoadC					Integer32,
		upsApm160snmp_324_Module4outputCrestFactorA					Integer32,
		upsApm160snmp_325_Module4outputCrestFactorB					Integer32,
		upsApm160snmp_326_Module4outputCrestFactorC					Integer32,
		upsApm160snmp_327_Module4bypassVoltageA					Integer32,
		upsApm160snmp_328_Module4bypassVoltageB					Integer32,
		upsApm160snmp_329_Module4bypassVoltageC					Integer32,
		upsApm160snmp_330_Module4bypassLineVoltageAB					Integer32,
		upsApm160snmp_331_Module4bypassLineVoltageBC					Integer32,
		upsApm160snmp_332_Module4bypassLineVoltageCA					Integer32,
		upsApm160snmp_333_Module4bypassFrequency					Integer32,
		upsApm160snmp_334_Module4batteryRemainsTime					Integer32,
		upsApm160snmp_335_Module4batteryPositiveVoltage					Integer32,
		upsApm160snmp_336_Module4batteryPositiveCurrent					Integer32,
		upsApm160snmp_337_Module4batteryNegativeVoltage					Integer32,
		upsApm160snmp_338_Module4batteryNegativeCurrent					Integer32,
		upsApm160snmp_339_Module4batteryAgingRate					Integer32,
		upsApm160snmp_340_Module4batteryTemperature					Integer32,
		upsApm160snmp_341_Branch1Current					Integer32,
		upsApm160snmp_342_Branch1Energy					Integer32,
		upsApm160snmp_343_Branch1SwitchStatus					INTEGER,
		upsApm160snmp_344_Branch1ActivePower					Integer32,
		upsApm160snmp_345_Branch1ApparentPower					Integer32,
		upsApm160snmp_346_Branch1THDi					Integer32,
		upsApm160snmp_347_Branch1RatedCurrent					Integer32,
		upsApm160snmp_348_Branch1LoadRatio					Integer32,
		upsApm160snmp_349_Branch1PowerFactor					Integer32,
		upsApm160snmp_350_Branch1Voltage					Integer32,
		upsApm160snmp_351_Branch2Current					Integer32,
		upsApm160snmp_352_Branch2Energy					Integer32,
		upsApm160snmp_353_Branch2SwitchStatus					INTEGER,
		upsApm160snmp_354_Branch2ActivePower					Integer32,
		upsApm160snmp_355_Branch2ApparentPower					Integer32,
		upsApm160snmp_356_Branch2THDi					Integer32,
		upsApm160snmp_357_Branch2RatedCurrent					Integer32,
		upsApm160snmp_358_Branch2LoadRatio					Integer32,
		upsApm160snmp_359_Branch2PowerFactor					Integer32,
		upsApm160snmp_360_Branch2Voltage					Integer32,
		upsApm160snmp_361_Branch3Current					Integer32,
		upsApm160snmp_362_Branch3Energy					Integer32,
		upsApm160snmp_363_Branch3SwitchStatus					INTEGER,
		upsApm160snmp_364_Branch3ActivePower					Integer32,
		upsApm160snmp_365_Branch3ApparentPower					Integer32,
		upsApm160snmp_366_Branch3THDi					Integer32,
		upsApm160snmp_367_Branch3RatedCurrent					Integer32,
		upsApm160snmp_368_Branch3LoadRatio					Integer32,
		upsApm160snmp_369_Branch3PowerFactor					Integer32,
		upsApm160snmp_370_Branch3Voltage					Integer32,
		upsApm160snmp_371_Branch4Current					Integer32,
		upsApm160snmp_372_Branch4Energy					Integer32,
		upsApm160snmp_373_Branch4SwitchStatus					INTEGER,
		upsApm160snmp_374_Branch4ActivePower					Integer32,
		upsApm160snmp_375_Branch4ApparentPower					Integer32,
		upsApm160snmp_376_Branch4THDi					Integer32,
		upsApm160snmp_377_Branch4RatedCurrent					Integer32,
		upsApm160snmp_378_Branch4LoadRatio					Integer32,
		upsApm160snmp_379_Branch4PowerFactor					Integer32,
		upsApm160snmp_380_Branch4Voltage					Integer32,
		upsApm160snmp_381_Branch5Current					Integer32,
		upsApm160snmp_382_Branch5Energy					Integer32,
		upsApm160snmp_383_Branch5SwitchStatus					INTEGER,
		upsApm160snmp_384_Branch5ActivePower					Integer32,
		upsApm160snmp_385_Branch5ApparentPower					Integer32,
		upsApm160snmp_386_Branch5THDi					Integer32,
		upsApm160snmp_387_Branch5RatedCurrent					Integer32,
		upsApm160snmp_388_Branch5LoadRatio					Integer32,
		upsApm160snmp_389_Branch5PowerFactor					Integer32,
		upsApm160snmp_390_Branch5Voltage					Integer32,
		upsApm160snmp_391_Branch6Current					Integer32,
		upsApm160snmp_392_Branch6Energy					Integer32,
		upsApm160snmp_393_Branch6SwitchStatus					INTEGER,
		upsApm160snmp_394_Branch6ActivePower					Integer32,
		upsApm160snmp_395_Branch6ApparentPower					Integer32,
		upsApm160snmp_396_Branch6THDi					Integer32,
		upsApm160snmp_397_Branch6RatedCurrent					Integer32,
		upsApm160snmp_398_Branch6LoadRatio					Integer32,
		upsApm160snmp_399_Branch6PowerFactor					Integer32,
		upsApm160snmp_400_Branch6Voltage					Integer32,
		upsApm160snmp_401_Branch7Current					Integer32,
		upsApm160snmp_402_Branch7Energy					Integer32,
		upsApm160snmp_403_Branch7SwitchStatus					INTEGER,
		upsApm160snmp_404_Branch7ActivePower					Integer32,
		upsApm160snmp_405_Branch7ApparentPower					Integer32,
		upsApm160snmp_406_Branch7THDi					Integer32,
		upsApm160snmp_407_Branch7RatedCurrent					Integer32,
		upsApm160snmp_408_Branch7LoadRatio					Integer32,
		upsApm160snmp_409_Branch7PowerFactor					Integer32,
		upsApm160snmp_410_Branch7Voltage					Integer32,
		upsApm160snmp_411_Branch8Current					Integer32,
		upsApm160snmp_412_Branch8Energy					Integer32,
		upsApm160snmp_413_Branch8SwitchStatus					INTEGER,
		upsApm160snmp_414_Branch8ActivePower					Integer32,
		upsApm160snmp_415_Branch8ApparentPower					Integer32,
		upsApm160snmp_416_Branch8THDi					Integer32,
		upsApm160snmp_417_Branch8RatedCurrent					Integer32,
		upsApm160snmp_418_Branch8LoadRatio					Integer32,
		upsApm160snmp_419_Branch8PowerFactor					Integer32,
		upsApm160snmp_420_Branch8Voltage					Integer32,
		upsApm160snmp_421_Branch9Current					Integer32,
		upsApm160snmp_422_Branch9Energy					Integer32,
		upsApm160snmp_423_Branch9SwitchStatus					INTEGER,
		upsApm160snmp_424_Branch9ActivePower					Integer32,
		upsApm160snmp_425_Branch9ApparentPower					Integer32,
		upsApm160snmp_426_Branch9THDi					Integer32,
		upsApm160snmp_427_Branch9RatedCurrent					Integer32,
		upsApm160snmp_428_Branch9LoadRatio					Integer32,
		upsApm160snmp_429_Branch9PowerFactor					Integer32,
		upsApm160snmp_430_Branch9Voltage					Integer32,
		upsApm160snmp_431_Branch10Current					Integer32,
		upsApm160snmp_432_Branch10Energy					Integer32,
		upsApm160snmp_433_Branch10SwitchStatus					INTEGER,
		upsApm160snmp_434_Branch10ActivePower					Integer32,
		upsApm160snmp_435_Branch10ApparentPower					Integer32,
		upsApm160snmp_436_Branch10THDi					Integer32,
		upsApm160snmp_437_Branch10RatedCurrent					Integer32,
		upsApm160snmp_438_Branch10LoadRatio					Integer32,
		upsApm160snmp_439_Branch10PowerFactor					Integer32,
		upsApm160snmp_440_Branch10Voltage					Integer32,
		upsApm160snmp_441_Branch11Current					Integer32,
		upsApm160snmp_442_Branch11Energy					Integer32,
		upsApm160snmp_443_Branch11SwitchStatus					INTEGER,
		upsApm160snmp_444_Branch11ActivePower					Integer32,
		upsApm160snmp_445_Branch11ApparentPower					Integer32,
		upsApm160snmp_446_Branch11THDi					Integer32,
		upsApm160snmp_447_Branch11RatedCurrent					Integer32,
		upsApm160snmp_448_Branch11LoadRatio					Integer32,
		upsApm160snmp_449_Branch11PowerFactor					Integer32,
		upsApm160snmp_450_Branch11Voltage					Integer32,
		upsApm160snmp_451_Branch12Current					Integer32,
		upsApm160snmp_452_Branch12Energy					Integer32,
		upsApm160snmp_453_Branch12SwitchStatus					INTEGER,
		upsApm160snmp_454_Branch12ActivePower					Integer32,
		upsApm160snmp_455_Branch12ApparentPower					Integer32,
		upsApm160snmp_456_Branch12THDi					Integer32,
		upsApm160snmp_457_Branch12RatedCurrent					Integer32,
		upsApm160snmp_458_Branch12LoadRatio					Integer32,
		upsApm160snmp_459_Branch12PowerFactor					Integer32,
		upsApm160snmp_460_Branch12Voltage					Integer32,
		upsApm160snmp_461_Branch13Current					Integer32,
		upsApm160snmp_462_Branch13Energy					Integer32,
		upsApm160snmp_463_Branch13SwitchStatus					INTEGER,
		upsApm160snmp_464_Branch13ActivePower					Integer32,
		upsApm160snmp_465_Branch13ApparentPower					Integer32,
		upsApm160snmp_466_Branch13THDi					Integer32,
		upsApm160snmp_467_Branch13RatedCurrent					Integer32,
		upsApm160snmp_468_Branch13LoadRatio					Integer32,
		upsApm160snmp_469_Branch13PowerFactor					Integer32,
		upsApm160snmp_470_Branch13Voltage					Integer32,
		upsApm160snmp_471_Branch14Current					Integer32,
		upsApm160snmp_472_Branch14Energy					Integer32,
		upsApm160snmp_473_Branch14SwitchStatus					INTEGER,
		upsApm160snmp_474_Branch14ActivePower					Integer32,
		upsApm160snmp_475_Branch14ApparentPower					Integer32,
		upsApm160snmp_476_Branch14THDi					Integer32,
		upsApm160snmp_477_Branch14RatedCurrent					Integer32,
		upsApm160snmp_478_Branch14LoadRatio					Integer32,
		upsApm160snmp_479_Branch14PowerFactor					Integer32,
		upsApm160snmp_480_Branch14Voltage					Integer32,
		upsApm160snmp_481_Branch15Current					Integer32,
		upsApm160snmp_482_Branch15Energy					Integer32,
		upsApm160snmp_483_Branch15SwitchStatus					INTEGER,
		upsApm160snmp_484_Branch15ActivePower					Integer32,
		upsApm160snmp_485_Branch15ApparentPower					Integer32,
		upsApm160snmp_486_Branch15THDi					Integer32,
		upsApm160snmp_487_Branch15RatedCurrent					Integer32,
		upsApm160snmp_488_Branch15LoadRatio					Integer32,
		upsApm160snmp_489_Branch15PowerFactor					Integer32,
		upsApm160snmp_490_Branch15Voltage					Integer32,
		upsApm160snmp_491_Branch16Current					Integer32,
		upsApm160snmp_492_Branch16Energy					Integer32,
		upsApm160snmp_493_Branch16SwitchStatus					INTEGER,
		upsApm160snmp_494_Branch16ActivePower					Integer32,
		upsApm160snmp_495_Branch16ApparentPower					Integer32,
		upsApm160snmp_496_Branch16THDi					Integer32,
		upsApm160snmp_497_Branch16RatedCurrent					Integer32,
		upsApm160snmp_498_Branch16LoadRatio					Integer32,
		upsApm160snmp_499_Branch16PowerFactor					Integer32,
		upsApm160snmp_500_Branch16Voltage					Integer32,
		upsApm160snmp_501_Branch17Current					Integer32,
		upsApm160snmp_502_Branch17Energy					Integer32,
		upsApm160snmp_503_Branch17SwitchStatus					INTEGER,
		upsApm160snmp_504_Branch17ActivePower					Integer32,
		upsApm160snmp_505_Branch17ApparentPower					Integer32,
		upsApm160snmp_506_Branch17THDi					Integer32,
		upsApm160snmp_507_Branch17RatedCurrent					Integer32,
		upsApm160snmp_508_Branch17LoadRatio					Integer32,
		upsApm160snmp_509_Branch17PowerFactor					Integer32,
		upsApm160snmp_510_Branch17Voltage					Integer32,
		upsApm160snmp_511_Branch18Current					Integer32,
		upsApm160snmp_512_Branch18Energy					Integer32,
		upsApm160snmp_513_Branch18SwitchStatus					INTEGER,
		upsApm160snmp_514_Branch18ActivePower					Integer32,
		upsApm160snmp_515_Branch18ApparentPower					Integer32,
		upsApm160snmp_516_Branch18THDi					Integer32,
		upsApm160snmp_517_Branch18RatedCurrent					Integer32,
		upsApm160snmp_518_Branch18LoadRatio					Integer32,
		upsApm160snmp_519_Branch18PowerFactor					Integer32,
		upsApm160snmp_520_Branch18Voltage					Integer32,
		upsApm160snmp_521_Branch19Current					Integer32,
		upsApm160snmp_522_Branch19Energy					Integer32,
		upsApm160snmp_523_Branch19SwitchStatus					INTEGER,
		upsApm160snmp_524_Branch19ActivePower					Integer32,
		upsApm160snmp_525_Branch19ApparentPower					Integer32,
		upsApm160snmp_526_Branch19THDi					Integer32,
		upsApm160snmp_527_Branch19RatedCurrent					Integer32,
		upsApm160snmp_528_Branch19LoadRatio					Integer32,
		upsApm160snmp_529_Branch19PowerFactor					Integer32,
		upsApm160snmp_530_Branch19Voltage					Integer32,
		upsApm160snmp_531_Branch20Current					Integer32,
		upsApm160snmp_532_Branch20Energy					Integer32,
		upsApm160snmp_533_Branch20SwitchStatus					INTEGER,
		upsApm160snmp_534_Branch20ActivePower					Integer32,
		upsApm160snmp_535_Branch20ApparentPower					Integer32,
		upsApm160snmp_536_Branch20THDi					Integer32,
		upsApm160snmp_537_Branch20RatedCurrent					Integer32,
		upsApm160snmp_538_Branch20LoadRatio					Integer32,
		upsApm160snmp_539_Branch20PowerFactor					Integer32,
		upsApm160snmp_540_Branch20Voltage					Integer32,
		upsApm160snmp_541_Branch21Current					Integer32,
		upsApm160snmp_542_Branch21Energy					Integer32,
		upsApm160snmp_543_Branch21SwitchStatus					INTEGER,
		upsApm160snmp_544_Branch21ActivePower					Integer32,
		upsApm160snmp_545_Branch21ApparentPower					Integer32,
		upsApm160snmp_546_Branch21THDi					Integer32,
		upsApm160snmp_547_Branch21RatedCurrent					Integer32,
		upsApm160snmp_548_Branch21LoadRatio					Integer32,
		upsApm160snmp_549_Branch21PowerFactor					Integer32,
		upsApm160snmp_550_Branch21Voltage					Integer32,
		upsApm160snmp_551_Branch22Current					Integer32,
		upsApm160snmp_552_Branch22Energy					Integer32,
		upsApm160snmp_553_Branch22SwitchStatus					INTEGER,
		upsApm160snmp_554_Branch22ActivePower					Integer32,
		upsApm160snmp_555_Branch22ApparentPower					Integer32,
		upsApm160snmp_556_Branch22THDi					Integer32,
		upsApm160snmp_557_Branch22RatedCurrent					Integer32,
		upsApm160snmp_558_Branch22LoadRatio					Integer32,
		upsApm160snmp_559_Branch22PowerFactor					Integer32,
		upsApm160snmp_560_Branch22Voltage					Integer32,
		upsApm160snmp_561_Branch23Current					Integer32,
		upsApm160snmp_562_Branch23Energy					Integer32,
		upsApm160snmp_563_Branch23SwitchStatus					INTEGER,
		upsApm160snmp_564_Branch23ActivePower					Integer32,
		upsApm160snmp_565_Branch23ApparentPower					Integer32,
		upsApm160snmp_566_Branch23THDi					Integer32,
		upsApm160snmp_567_Branch23RatedCurrent					Integer32,
		upsApm160snmp_568_Branch23LoadRatio					Integer32,
		upsApm160snmp_569_Branch23PowerFactor					Integer32,
		upsApm160snmp_570_Branch23Voltage					Integer32,
		upsApm160snmp_571_Branch24Current					Integer32,
		upsApm160snmp_572_Branch24Energy					Integer32,
		upsApm160snmp_573_Branch24SwitchStatus					INTEGER,
		upsApm160snmp_574_Branch24ActivePower					Integer32,
		upsApm160snmp_575_Branch24ApparentPower					Integer32,
		upsApm160snmp_576_Branch24THDi					Integer32,
		upsApm160snmp_577_Branch24RatedCurrent					Integer32,
		upsApm160snmp_578_Branch24LoadRatio					Integer32,
		upsApm160snmp_579_Branch24PowerFactor					Integer32,
		upsApm160snmp_580_Branch24Voltage					Integer32,
		upsApm160snmp_581_Branch25Current					Integer32,
		upsApm160snmp_582_Branch25Energy					Integer32,
		upsApm160snmp_583_Branch25SwitchStatus					INTEGER,
		upsApm160snmp_584_Branch25ActivePower					Integer32,
		upsApm160snmp_585_Branch25ApparentPower					Integer32,
		upsApm160snmp_586_Branch25THDi					Integer32,
		upsApm160snmp_587_Branch25RatedCurrent					Integer32,
		upsApm160snmp_588_Branch25LoadRatio					Integer32,
		upsApm160snmp_589_Branch25PowerFactor					Integer32,
		upsApm160snmp_590_Branch25Voltage					Integer32,
		upsApm160snmp_591_Branch26Current					Integer32,
		upsApm160snmp_592_Branch26Energy					Integer32,
		upsApm160snmp_593_Branch26SwitchStatus					INTEGER,
		upsApm160snmp_594_Branch26ActivePower					Integer32,
		upsApm160snmp_595_Branch26ApparentPower					Integer32,
		upsApm160snmp_596_Branch26THDi					Integer32,
		upsApm160snmp_597_Branch26RatedCurrent					Integer32,
		upsApm160snmp_598_Branch26LoadRatio					Integer32,
		upsApm160snmp_599_Branch26PowerFactor					Integer32,
		upsApm160snmp_600_Branch26Voltage					Integer32,
		upsApm160snmp_601_Branch27Current					Integer32,
		upsApm160snmp_602_Branch27Energy					Integer32,
		upsApm160snmp_603_Branch27SwitchStatus					INTEGER,
		upsApm160snmp_604_Branch27ActivePower					Integer32,
		upsApm160snmp_605_Branch27ApparentPower					Integer32,
		upsApm160snmp_606_Branch27THDi					Integer32,
		upsApm160snmp_607_Branch27RatedCurrent					Integer32,
		upsApm160snmp_608_Branch27LoadRatio					Integer32,
		upsApm160snmp_609_Branch27PowerFactor					Integer32,
		upsApm160snmp_610_Branch27Voltage					Integer32,
		upsApm160snmp_611_Branch28Current					Integer32,
		upsApm160snmp_612_Branch28Energy					Integer32,
		upsApm160snmp_613_Branch28SwitchStatus					INTEGER,
		upsApm160snmp_614_Branch28ActivePower					Integer32,
		upsApm160snmp_615_Branch28ApparentPower					Integer32,
		upsApm160snmp_616_Branch28THDi					Integer32,
		upsApm160snmp_617_Branch28RatedCurrent					Integer32,
		upsApm160snmp_618_Branch28LoadRatio					Integer32,
		upsApm160snmp_619_Branch28PowerFactor					Integer32,
		upsApm160snmp_620_Branch28Voltage					Integer32,
		upsApm160snmp_621_Branch29Current					Integer32,
		upsApm160snmp_622_Branch29Energy					Integer32,
		upsApm160snmp_623_Branch29SwitchStatus					INTEGER,
		upsApm160snmp_624_Branch29ActivePower					Integer32,
		upsApm160snmp_625_Branch29ApparentPower					Integer32,
		upsApm160snmp_626_Branch29THDi					Integer32,
		upsApm160snmp_627_Branch29RatedCurrent					Integer32,
		upsApm160snmp_628_Branch29LoadRatio					Integer32,
		upsApm160snmp_629_Branch29PowerFactor					Integer32,
		upsApm160snmp_630_Branch29Voltage					Integer32,
		upsApm160snmp_631_Branch30Current					Integer32,
		upsApm160snmp_632_Branch30Energy					Integer32,
		upsApm160snmp_633_Branch30SwitchStatus					INTEGER,
		upsApm160snmp_634_Branch30ActivePower					Integer32,
		upsApm160snmp_635_Branch30ApparentPower					Integer32,
		upsApm160snmp_636_Branch30THDi					Integer32,
		upsApm160snmp_637_Branch30RatedCurrent					Integer32,
		upsApm160snmp_638_Branch30LoadRatio					Integer32,
		upsApm160snmp_639_Branch30PowerFactor					Integer32,
		upsApm160snmp_640_Branch30Voltage					Integer32,
		upsApm160snmp_641_Branch31Current					Integer32,
		upsApm160snmp_642_Branch31Energy					Integer32,
		upsApm160snmp_643_Branch31SwitchStatus					INTEGER,
		upsApm160snmp_644_Branch31ActivePower					Integer32,
		upsApm160snmp_645_Branch31ApparentPower					Integer32,
		upsApm160snmp_646_Branch31THDi					Integer32,
		upsApm160snmp_647_Branch31RatedCurrent					Integer32,
		upsApm160snmp_648_Branch31LoadRatio					Integer32,
		upsApm160snmp_649_Branch31PowerFactor					Integer32,
		upsApm160snmp_650_Branch31Voltage					Integer32,
		upsApm160snmp_651_Branch32Current					Integer32,
		upsApm160snmp_652_Branch32Energy					Integer32,
		upsApm160snmp_653_Branch32SwitchStatus					INTEGER,
		upsApm160snmp_654_Branch32ActivePower					Integer32,
		upsApm160snmp_655_Branch32ApparentPower					Integer32,
		upsApm160snmp_656_Branch32THDi					Integer32,
		upsApm160snmp_657_Branch32RatedCurrent					Integer32,
		upsApm160snmp_658_Branch32LoadRatio					Integer32,
		upsApm160snmp_659_Branch32PowerFactor					Integer32,
		upsApm160snmp_660_Branch32Voltage					Integer32,
		upsApm160snmp_661_Branch33Current					Integer32,
		upsApm160snmp_662_Branch33Energy					Integer32,
		upsApm160snmp_663_Branch33SwitchStatus					INTEGER,
		upsApm160snmp_664_Branch33ActivePower					Integer32,
		upsApm160snmp_665_Branch33ApparentPower					Integer32,
		upsApm160snmp_666_Branch33THDi					Integer32,
		upsApm160snmp_667_Branch33RatedCurrent					Integer32,
		upsApm160snmp_668_Branch33LoadRatio					Integer32,
		upsApm160snmp_669_Branch33PowerFactor					Integer32,
		upsApm160snmp_670_Branch33Voltage					Integer32,
		upsApm160snmp_671_Branch34Current					Integer32,
		upsApm160snmp_672_Branch34Energy					Integer32,
		upsApm160snmp_673_Branch34SwitchStatus					INTEGER,
		upsApm160snmp_674_Branch34ActivePower					Integer32,
		upsApm160snmp_675_Branch34ApparentPower					Integer32,
		upsApm160snmp_676_Branch34THDi					Integer32,
		upsApm160snmp_677_Branch34RatedCurrent					Integer32,
		upsApm160snmp_678_Branch34LoadRatio					Integer32,
		upsApm160snmp_679_Branch34PowerFactor					Integer32,
		upsApm160snmp_680_Branch34Voltage					Integer32,
		upsApm160snmp_681_Branch35Current					Integer32,
		upsApm160snmp_682_Branch35Energy					Integer32,
		upsApm160snmp_683_Branch35SwitchStatus					INTEGER,
		upsApm160snmp_684_Branch35ActivePower					Integer32,
		upsApm160snmp_685_Branch35ApparentPower					Integer32,
		upsApm160snmp_686_Branch35THDi					Integer32,
		upsApm160snmp_687_Branch35RatedCurrent					Integer32,
		upsApm160snmp_688_Branch35LoadRatio					Integer32,
		upsApm160snmp_689_Branch35PowerFactor					Integer32,
		upsApm160snmp_690_Branch35Voltage					Integer32,
		upsApm160snmp_691_Branch36Current					Integer32,
		upsApm160snmp_692_Branch36Energy					Integer32,
		upsApm160snmp_693_Branch36SwitchStatus					INTEGER,
		upsApm160snmp_694_Branch36ActivePower					Integer32,
		upsApm160snmp_695_Branch36ApparentPower					Integer32,
		upsApm160snmp_696_Branch36THDi					Integer32,
		upsApm160snmp_697_Branch36RatedCurrent					Integer32,
		upsApm160snmp_698_Branch36LoadRatio					Integer32,
		upsApm160snmp_699_Branch36PowerFactor					Integer32,
		upsApm160snmp_700_Branch36Voltage					Integer32,
		upsApm160snmp_701_Branch37Current					Integer32,
		upsApm160snmp_702_Branch37Energy					Integer32,
		upsApm160snmp_703_Branch37SwitchStatus					INTEGER,
		upsApm160snmp_704_Branch37ActivePower					Integer32,
		upsApm160snmp_705_Branch37ApparentPower					Integer32,
		upsApm160snmp_706_Branch37THDi					Integer32,
		upsApm160snmp_707_Branch37RatedCurrent					Integer32,
		upsApm160snmp_708_Branch37LoadRatio					Integer32,
		upsApm160snmp_709_Branch37PowerFactor					Integer32,
		upsApm160snmp_710_Branch37Voltage					Integer32,
		upsApm160snmp_711_Branch38Current					Integer32,
		upsApm160snmp_712_Branch38Energy					Integer32,
		upsApm160snmp_713_Branch38SwitchStatus					INTEGER,
		upsApm160snmp_714_Branch38ActivePower					Integer32,
		upsApm160snmp_715_Branch38ApparentPower					Integer32,
		upsApm160snmp_716_Branch38THDi					Integer32,
		upsApm160snmp_717_Branch38RatedCurrent					Integer32,
		upsApm160snmp_718_Branch38LoadRatio					Integer32,
		upsApm160snmp_719_Branch38PowerFactor					Integer32,
		upsApm160snmp_720_Branch38Voltage					Integer32,
		upsApm160snmp_721_Branch39Current					Integer32,
		upsApm160snmp_722_Branch39Energy					Integer32,
		upsApm160snmp_723_Branch39SwitchStatus					INTEGER,
		upsApm160snmp_724_Branch39ActivePower					Integer32,
		upsApm160snmp_725_Branch39ApparentPower					Integer32,
		upsApm160snmp_726_Branch39THDi					Integer32,
		upsApm160snmp_727_Branch39RatedCurrent					Integer32,
		upsApm160snmp_728_Branch39LoadRatio					Integer32,
		upsApm160snmp_729_Branch39PowerFactor					Integer32,
		upsApm160snmp_730_Branch39Voltage					Integer32,
		upsApm160snmp_731_Branch40Current					Integer32,
		upsApm160snmp_732_Branch40Energy					Integer32,
		upsApm160snmp_733_Branch40SwitchStatus					INTEGER,
		upsApm160snmp_734_Branch40ActivePower					Integer32,
		upsApm160snmp_735_Branch40ApparentPower					Integer32,
		upsApm160snmp_736_Branch40THDi					Integer32,
		upsApm160snmp_737_Branch40RatedCurrent					Integer32,
		upsApm160snmp_738_Branch40LoadRatio					Integer32,
		upsApm160snmp_739_Branch40PowerFactor					Integer32,
		upsApm160snmp_740_Branch40Voltage					Integer32,
		upsApm160snmp_741_Branch41Current					Integer32,
		upsApm160snmp_742_Branch41Energy					Integer32,
		upsApm160snmp_743_Branch41SwitchStatus					INTEGER,
		upsApm160snmp_744_Branch41ActivePower					Integer32,
		upsApm160snmp_745_Branch41ApparentPower					Integer32,
		upsApm160snmp_746_Branch41THDi					Integer32,
		upsApm160snmp_747_Branch41RatedCurrent					Integer32,
		upsApm160snmp_748_Branch41LoadRatio					Integer32,
		upsApm160snmp_749_Branch41PowerFactor					Integer32,
		upsApm160snmp_750_Branch41Voltage					Integer32,
		upsApm160snmp_751_Branch42Current					Integer32,
		upsApm160snmp_752_Branch42Energy					Integer32,
		upsApm160snmp_753_Branch42SwitchStatus					INTEGER,
		upsApm160snmp_754_Branch42ActivePower					Integer32,
		upsApm160snmp_755_Branch42ApparentPower					Integer32,
		upsApm160snmp_756_Branch42THDi					Integer32,
		upsApm160snmp_757_Branch42RatedCurrent					Integer32,
		upsApm160snmp_758_Branch42LoadRatio					Integer32,
		upsApm160snmp_759_Branch42PowerFactor					Integer32,
		upsApm160snmp_760_Branch42Voltage					Integer32,
		upsApm160snmp_761_Branch43Current					Integer32,
		upsApm160snmp_762_Branch43Energy					Integer32,
		upsApm160snmp_763_Branch43SwitchStatus					INTEGER,
		upsApm160snmp_764_Branch43ActivePower					Integer32,
		upsApm160snmp_765_Branch43ApparentPower					Integer32,
		upsApm160snmp_766_Branch43THDi					Integer32,
		upsApm160snmp_767_Branch43RatedCurrent					Integer32,
		upsApm160snmp_768_Branch43LoadRatio					Integer32,
		upsApm160snmp_769_Branch43PowerFactor					Integer32,
		upsApm160snmp_770_Branch43Voltage					Integer32,
		upsApm160snmp_771_Branch44Current					Integer32,
		upsApm160snmp_772_Branch44Energy					Integer32,
		upsApm160snmp_773_Branch44SwitchStatus					INTEGER,
		upsApm160snmp_774_Branch44ActivePower					Integer32,
		upsApm160snmp_775_Branch44ApparentPower					Integer32,
		upsApm160snmp_776_Branch44THDi					Integer32,
		upsApm160snmp_777_Branch44RatedCurrent					Integer32,
		upsApm160snmp_778_Branch44LoadRatio					Integer32,
		upsApm160snmp_779_Branch44PowerFactor					Integer32,
		upsApm160snmp_780_Branch44Voltage					Integer32,
		upsApm160snmp_781_Branch45Current					Integer32,
		upsApm160snmp_782_Branch45Energy					Integer32,
		upsApm160snmp_783_Branch45SwitchStatus					INTEGER,
		upsApm160snmp_784_Branch45ActivePower					Integer32,
		upsApm160snmp_785_Branch45ApparentPower					Integer32,
		upsApm160snmp_786_Branch45THDi					Integer32,
		upsApm160snmp_787_Branch45RatedCurrent					Integer32,
		upsApm160snmp_788_Branch45LoadRatio					Integer32,
		upsApm160snmp_789_Branch45PowerFactor					Integer32,
		upsApm160snmp_790_Branch45Voltage					Integer32,
		upsApm160snmp_791_Branch46Current					Integer32,
		upsApm160snmp_792_Branch46Energy					Integer32,
		upsApm160snmp_793_Branch46SwitchStatus					INTEGER,
		upsApm160snmp_794_Branch46ActivePower					Integer32,
		upsApm160snmp_795_Branch46ApparentPower					Integer32,
		upsApm160snmp_796_Branch46THDi					Integer32,
		upsApm160snmp_797_Branch46RatedCurrent					Integer32,
		upsApm160snmp_798_Branch46LoadRatio					Integer32,
		upsApm160snmp_799_Branch46PowerFactor					Integer32,
		upsApm160snmp_800_Branch46Voltage					Integer32,
		upsApm160snmp_801_Branch47Current					Integer32,
		upsApm160snmp_802_Branch47Energy					Integer32,
		upsApm160snmp_803_Branch47SwitchStatus					INTEGER,
		upsApm160snmp_804_Branch47ActivePower					Integer32,
		upsApm160snmp_805_Branch47ApparentPower					Integer32,
		upsApm160snmp_806_Branch47THDi					Integer32,
		upsApm160snmp_807_Branch47RatedCurrent					Integer32,
		upsApm160snmp_808_Branch47LoadRatio					Integer32,
		upsApm160snmp_809_Branch47PowerFactor					Integer32,
		upsApm160snmp_810_Branch47Voltage					Integer32,
		upsApm160snmp_811_Branch48Current					Integer32,
		upsApm160snmp_812_Branch48Energy					Integer32,
		upsApm160snmp_813_Branch48SwitchStatus					INTEGER,
		upsApm160snmp_814_Branch48ActivePower					Integer32,
		upsApm160snmp_815_Branch48ApparentPower					Integer32,
		upsApm160snmp_816_Branch48THDi					Integer32,
		upsApm160snmp_817_Branch48RatedCurrent					Integer32,
		upsApm160snmp_818_Branch48LoadRatio					Integer32,
		upsApm160snmp_819_Branch48PowerFactor					Integer32,
		upsApm160snmp_820_Branch48Voltage					Integer32,
		upsApm160snmp_821_Branch49Current					Integer32,
		upsApm160snmp_822_Branch49Energy					Integer32,
		upsApm160snmp_823_Branch49SwitchStatus					INTEGER,
		upsApm160snmp_824_Branch49ActivePower					Integer32,
		upsApm160snmp_825_Branch49ApparentPower					Integer32,
		upsApm160snmp_826_Branch49THDi					Integer32,
		upsApm160snmp_827_Branch49RatedCurrent					Integer32,
		upsApm160snmp_828_Branch49LoadRatio					Integer32,
		upsApm160snmp_829_Branch49PowerFactor					Integer32,
		upsApm160snmp_830_Branch49Voltage					Integer32,
		upsApm160snmp_831_Branch50Current					Integer32,
		upsApm160snmp_832_Branch50Energy					Integer32,
		upsApm160snmp_833_Branch50SwitchStatus					INTEGER,
		upsApm160snmp_834_Branch50ActivePower					Integer32,
		upsApm160snmp_835_Branch50ApparentPower					Integer32,
		upsApm160snmp_836_Branch50THDi					Integer32,
		upsApm160snmp_837_Branch50RatedCurrent					Integer32,
		upsApm160snmp_838_Branch50LoadRatio					Integer32,
		upsApm160snmp_839_Branch50PowerFactor					Integer32,
		upsApm160snmp_840_Branch50Voltage					Integer32,
		upsApm160snmp_841_Branch51Current					Integer32,
		upsApm160snmp_842_Branch51Energy					Integer32,
		upsApm160snmp_843_Branch51SwitchStatus					INTEGER,
		upsApm160snmp_844_Branch51ActivePower					Integer32,
		upsApm160snmp_845_Branch51ApparentPower					Integer32,
		upsApm160snmp_846_Branch51THDi					Integer32,
		upsApm160snmp_847_Branch51RatedCurrent					Integer32,
		upsApm160snmp_848_Branch51LoadRatio					Integer32,
		upsApm160snmp_849_Branch51PowerFactor					Integer32,
		upsApm160snmp_850_Branch51Voltage					Integer32,
		upsApm160snmp_851_Branch52Current					Integer32,
		upsApm160snmp_852_Branch52Energy					Integer32,
		upsApm160snmp_853_Branch52SwitchStatus					INTEGER,
		upsApm160snmp_854_Branch52ActivePower					Integer32,
		upsApm160snmp_855_Branch52ApparentPower					Integer32,
		upsApm160snmp_856_Branch52THDi					Integer32,
		upsApm160snmp_857_Branch52RatedCurrent					Integer32,
		upsApm160snmp_858_Branch52LoadRatio					Integer32,
		upsApm160snmp_859_Branch52PowerFactor					Integer32,
		upsApm160snmp_860_Branch52Voltage					Integer32,
		upsApm160snmp_861_Branch53Current					Integer32,
		upsApm160snmp_862_Branch53Energy					Integer32,
		upsApm160snmp_863_Branch53SwitchStatus					INTEGER,
		upsApm160snmp_864_Branch53ActivePower					Integer32,
		upsApm160snmp_865_Branch53ApparentPower					Integer32,
		upsApm160snmp_866_Branch53THDi					Integer32,
		upsApm160snmp_867_Branch53RatedCurrent					Integer32,
		upsApm160snmp_868_Branch53LoadRatio					Integer32,
		upsApm160snmp_869_Branch53PowerFactor					Integer32,
		upsApm160snmp_870_Branch53Voltage					Integer32,
		upsApm160snmp_871_Branch54Current					Integer32,
		upsApm160snmp_872_Branch54Energy					Integer32,
		upsApm160snmp_873_Branch54SwitchStatus					INTEGER,
		upsApm160snmp_874_Branch54ActivePower					Integer32,
		upsApm160snmp_875_Branch54ApparentPower					Integer32,
		upsApm160snmp_876_Branch54THDi					Integer32,
		upsApm160snmp_877_Branch54RatedCurrent					Integer32,
		upsApm160snmp_878_Branch54LoadRatio					Integer32,
		upsApm160snmp_879_Branch54PowerFactor					Integer32,
		upsApm160snmp_880_Branch54Voltage					Integer32,
		upsApm160snmp_881_Branch55Current					Integer32,
		upsApm160snmp_882_Branch55Energy					Integer32,
		upsApm160snmp_883_Branch55SwitchStatus					INTEGER,
		upsApm160snmp_884_Branch55ActivePower					Integer32,
		upsApm160snmp_885_Branch55ApparentPower					Integer32,
		upsApm160snmp_886_Branch55THDi					Integer32,
		upsApm160snmp_887_Branch55RatedCurrent					Integer32,
		upsApm160snmp_888_Branch55LoadRatio					Integer32,
		upsApm160snmp_889_Branch55PowerFactor					Integer32,
		upsApm160snmp_890_Branch55Voltage					Integer32,
		upsApm160snmp_891_Branch56Current					Integer32,
		upsApm160snmp_892_Branch56Energy					Integer32,
		upsApm160snmp_893_Branch56SwitchStatus					INTEGER,
		upsApm160snmp_894_Branch56ActivePower					Integer32,
		upsApm160snmp_895_Branch56ApparentPower					Integer32,
		upsApm160snmp_896_Branch56THDi					Integer32,
		upsApm160snmp_897_Branch56RatedCurrent					Integer32,
		upsApm160snmp_898_Branch56LoadRatio					Integer32,
		upsApm160snmp_899_Branch56PowerFactor					Integer32,
		upsApm160snmp_900_Branch56Voltage					Integer32,
		upsApm160snmp_901_Branch57Current					Integer32,
		upsApm160snmp_902_Branch57Energy					Integer32,
		upsApm160snmp_903_Branch57SwitchStatus					INTEGER,
		upsApm160snmp_904_Branch57ActivePower					Integer32,
		upsApm160snmp_905_Branch57ApparentPower					Integer32,
		upsApm160snmp_906_Branch57THDi					Integer32,
		upsApm160snmp_907_Branch57RatedCurrent					Integer32,
		upsApm160snmp_908_Branch57LoadRatio					Integer32,
		upsApm160snmp_909_Branch57PowerFactor					Integer32,
		upsApm160snmp_910_Branch57Voltage					Integer32,
		upsApm160snmp_911_Branch58Current					Integer32,
		upsApm160snmp_912_Branch58Energy					Integer32,
		upsApm160snmp_913_Branch58SwitchStatus					INTEGER,
		upsApm160snmp_914_Branch58ActivePower					Integer32,
		upsApm160snmp_915_Branch58ApparentPower					Integer32,
		upsApm160snmp_916_Branch58THDi					Integer32,
		upsApm160snmp_917_Branch58RatedCurrent					Integer32,
		upsApm160snmp_918_Branch58LoadRatio					Integer32,
		upsApm160snmp_919_Branch58PowerFactor					Integer32,
		upsApm160snmp_920_Branch58Voltage					Integer32,
		upsApm160snmp_921_Branch59Current					Integer32,
		upsApm160snmp_922_Branch59Energy					Integer32,
		upsApm160snmp_923_Branch59SwitchStatus					INTEGER,
		upsApm160snmp_924_Branch59ActivePower					Integer32,
		upsApm160snmp_925_Branch59ApparentPower					Integer32,
		upsApm160snmp_926_Branch59THDi					Integer32,
		upsApm160snmp_927_Branch59RatedCurrent					Integer32,
		upsApm160snmp_928_Branch59LoadRatio					Integer32,
		upsApm160snmp_929_Branch59PowerFactor					Integer32,
		upsApm160snmp_930_Branch59Voltage					Integer32,
		upsApm160snmp_931_Branch60Current					Integer32,
		upsApm160snmp_932_Branch60Energy					Integer32,
		upsApm160snmp_933_Branch60SwitchStatus					INTEGER,
		upsApm160snmp_934_Branch60ActivePower					Integer32,
		upsApm160snmp_935_Branch60ApparentPower					Integer32,
		upsApm160snmp_936_Branch60THDi					Integer32,
		upsApm160snmp_937_Branch60RatedCurrent					Integer32,
		upsApm160snmp_938_Branch60LoadRatio					Integer32,
		upsApm160snmp_939_Branch60PowerFactor					Integer32,
		upsApm160snmp_940_Branch60Voltage					Integer32,
		upsApm160snmp_941_Branch61Current					Integer32,
		upsApm160snmp_942_Branch61Energy					Integer32,
		upsApm160snmp_943_Branch61SwitchStatus					INTEGER,
		upsApm160snmp_944_Branch61ActivePower					Integer32,
		upsApm160snmp_945_Branch61ApparentPower					Integer32,
		upsApm160snmp_946_Branch61THDi					Integer32,
		upsApm160snmp_947_Branch61RatedCurrent					Integer32,
		upsApm160snmp_948_Branch61LoadRatio					Integer32,
		upsApm160snmp_949_Branch61PowerFactor					Integer32,
		upsApm160snmp_950_Branch61Voltage					Integer32,
		upsApm160snmp_951_Branch62Current					Integer32,
		upsApm160snmp_952_Branch62Energy					Integer32,
		upsApm160snmp_953_Branch62SwitchStatus					INTEGER,
		upsApm160snmp_954_Branch62ActivePower					Integer32,
		upsApm160snmp_955_Branch62ApparentPower					Integer32,
		upsApm160snmp_956_Branch62THDi					Integer32,
		upsApm160snmp_957_Branch62RatedCurrent					Integer32,
		upsApm160snmp_958_Branch62LoadRatio					Integer32,
		upsApm160snmp_959_Branch62PowerFactor					Integer32,
		upsApm160snmp_960_Branch62Voltage					Integer32,
		upsApm160snmp_961_Branch63Current					Integer32,
		upsApm160snmp_962_Branch63Energy					Integer32,
		upsApm160snmp_963_Branch63SwitchStatus					INTEGER,
		upsApm160snmp_964_Branch63ActivePower					Integer32,
		upsApm160snmp_965_Branch63ApparentPower					Integer32,
		upsApm160snmp_966_Branch63THDi					Integer32,
		upsApm160snmp_967_Branch63RatedCurrent					Integer32,
		upsApm160snmp_968_Branch63LoadRatio					Integer32,
		upsApm160snmp_969_Branch63PowerFactor					Integer32,
		upsApm160snmp_970_Branch63Voltage					Integer32,
		upsApm160snmp_971_Branch64Current					Integer32,
		upsApm160snmp_972_Branch64Energy					Integer32,
		upsApm160snmp_973_Branch64SwitchStatus					INTEGER,
		upsApm160snmp_974_Branch64ActivePower					Integer32,
		upsApm160snmp_975_Branch64ApparentPower					Integer32,
		upsApm160snmp_976_Branch64THDi					Integer32,
		upsApm160snmp_977_Branch64RatedCurrent					Integer32,
		upsApm160snmp_978_Branch64LoadRatio					Integer32,
		upsApm160snmp_979_Branch64PowerFactor					Integer32,
		upsApm160snmp_980_Branch64Voltage					Integer32,
		upsApm160snmp_981_Branch65Current					Integer32,
		upsApm160snmp_982_Branch65Energy					Integer32,
		upsApm160snmp_983_Branch65SwitchStatus					INTEGER,
		upsApm160snmp_984_Branch65ActivePower					Integer32,
		upsApm160snmp_985_Branch65ApparentPower					Integer32,
		upsApm160snmp_986_Branch65THDi					Integer32,
		upsApm160snmp_987_Branch65RatedCurrent					Integer32,
		upsApm160snmp_988_Branch65LoadRatio					Integer32,
		upsApm160snmp_989_Branch65PowerFactor					Integer32,
		upsApm160snmp_990_Branch65Voltage					Integer32,
		upsApm160snmp_991_Branch66Current					Integer32,
		upsApm160snmp_992_Branch66Energy					Integer32,
		upsApm160snmp_993_Branch66SwitchStatus					INTEGER,
		upsApm160snmp_994_Branch66ActivePower					Integer32,
		upsApm160snmp_995_Branch66ApparentPower					Integer32,
		upsApm160snmp_996_Branch66THDi					Integer32,
		upsApm160snmp_997_Branch66RatedCurrent					Integer32,
		upsApm160snmp_998_Branch66LoadRatio					Integer32,
		upsApm160snmp_999_Branch66PowerFactor					Integer32,
		upsApm160snmp_1000_Branch66Voltage					Integer32,
		upsApm160snmp_1001_Branch67Current					Integer32,
		upsApm160snmp_1002_Branch67Energy					Integer32,
		upsApm160snmp_1003_Branch67SwitchStatus					INTEGER,
		upsApm160snmp_1004_Branch67ActivePower					Integer32,
		upsApm160snmp_1005_Branch67ApparentPower					Integer32,
		upsApm160snmp_1006_Branch67THDi					Integer32,
		upsApm160snmp_1007_Branch67RatedCurrent					Integer32,
		upsApm160snmp_1008_Branch67LoadRatio					Integer32,
		upsApm160snmp_1009_Branch67PowerFactor					Integer32,
		upsApm160snmp_1010_Branch67Voltage					Integer32,
		upsApm160snmp_1011_Branch68Current					Integer32,
		upsApm160snmp_1012_Branch68Energy					Integer32,
		upsApm160snmp_1013_Branch68SwitchStatus					INTEGER,
		upsApm160snmp_1014_Branch68ActivePower					Integer32,
		upsApm160snmp_1015_Branch68ApparentPower					Integer32,
		upsApm160snmp_1016_Branch68THDi					Integer32,
		upsApm160snmp_1017_Branch68RatedCurrent					Integer32,
		upsApm160snmp_1018_Branch68LoadRatio					Integer32,
		upsApm160snmp_1019_Branch68PowerFactor					Integer32,
		upsApm160snmp_1020_Branch68Voltage					Integer32,
		upsApm160snmp_1021_Branch69Current					Integer32,
		upsApm160snmp_1022_Branch69Energy					Integer32,
		upsApm160snmp_1023_Branch69SwitchStatus					INTEGER,
		upsApm160snmp_1024_Branch69ActivePower					Integer32,
		upsApm160snmp_1025_Branch69ApparentPower					Integer32,
		upsApm160snmp_1026_Branch69THDi					Integer32,
		upsApm160snmp_1027_Branch69RatedCurrent					Integer32,
		upsApm160snmp_1028_Branch69LoadRatio					Integer32,
		upsApm160snmp_1029_Branch69PowerFactor					Integer32,
		upsApm160snmp_1030_Branch69Voltage					Integer32,
		upsApm160snmp_1031_Branch70Current					Integer32,
		upsApm160snmp_1032_Branch70Energy					Integer32,
		upsApm160snmp_1033_Branch70SwitchStatus					INTEGER,
		upsApm160snmp_1034_Branch70ActivePower					Integer32,
		upsApm160snmp_1035_Branch70ApparentPower					Integer32,
		upsApm160snmp_1036_Branch70THDi					Integer32,
		upsApm160snmp_1037_Branch70RatedCurrent					Integer32,
		upsApm160snmp_1038_Branch70LoadRatio					Integer32,
		upsApm160snmp_1039_Branch70PowerFactor					Integer32,
		upsApm160snmp_1040_Branch70Voltage					Integer32,
		upsApm160snmp_1041_Branch71Current					Integer32,
		upsApm160snmp_1042_Branch71Energy					Integer32,
		upsApm160snmp_1043_Branch71SwitchStatus					INTEGER,
		upsApm160snmp_1044_Branch71ActivePower					Integer32,
		upsApm160snmp_1045_Branch71ApparentPower					Integer32,
		upsApm160snmp_1046_Branch71THDi					Integer32,
		upsApm160snmp_1047_Branch71RatedCurrent					Integer32,
		upsApm160snmp_1048_Branch71LoadRatio					Integer32,
		upsApm160snmp_1049_Branch71PowerFactor					Integer32,
		upsApm160snmp_1050_Branch71Voltage					Integer32,
		upsApm160snmp_1051_Branch72Current					Integer32,
		upsApm160snmp_1052_Branch72Energy					Integer32,
		upsApm160snmp_1053_Branch72SwitchStatus					INTEGER,
		upsApm160snmp_1054_Branch72ActivePower					Integer32,
		upsApm160snmp_1055_Branch72ApparentPower					Integer32,
		upsApm160snmp_1056_Branch72THDi					Integer32,
		upsApm160snmp_1057_Branch72RatedCurrent					Integer32,
		upsApm160snmp_1058_Branch72LoadRatio					Integer32,
		upsApm160snmp_1059_Branch72PowerFactor					Integer32,
		upsApm160snmp_1060_Branch72Voltage					Integer32,
		upsApm160snmp_1061_InputSource1CurrentA					Integer32,
		upsApm160snmp_1062_InputSource1CurrentB					Integer32,
		upsApm160snmp_1063_InputSource1CurrentC					Integer32,
		upsApm160snmp_1064_InputSource1EnergyA					Integer32,
		upsApm160snmp_1065_InputSource1EnergyB					Integer32,
		upsApm160snmp_1066_InputSource1EnergyC					Integer32,
		upsApm160snmp_1067_InputSource1SwitchStatusA					INTEGER,
		upsApm160snmp_1068_InputSource1SwitchStatusB					INTEGER,
		upsApm160snmp_1069_InputSource1SwitchStatusC					INTEGER,
		upsApm160snmp_1070_InputSource1ActivePowerA					Integer32,
		upsApm160snmp_1071_InputSource1ActivePowerB					Integer32,
		upsApm160snmp_1072_InputSource1ActivePowerC					Integer32,
		upsApm160snmp_1073_InputSource1ApparentPowerA					Integer32,
		upsApm160snmp_1074_InputSource1ApparentPowerB					Integer32,
		upsApm160snmp_1075_InputSource1ApparentPowerC					Integer32,
		upsApm160snmp_1076_InputSource1THDiA					Integer32,
		upsApm160snmp_1077_InputSource1THDiB					Integer32,
		upsApm160snmp_1078_InputSource1THDiC					Integer32,
		upsApm160snmp_1079_InputSource1RatedCurrentA					Integer32,
		upsApm160snmp_1080_InputSource1RatedCurrentB					Integer32,
		upsApm160snmp_1081_InputSource1RatedCurrentC					Integer32,
		upsApm160snmp_1082_InputSource1LoadRatioA					Integer32,
		upsApm160snmp_1083_InputSource1LoadRatioB					Integer32,
		upsApm160snmp_1084_InputSource1LoadRatioC					Integer32,
		upsApm160snmp_1085_InputSource1PowerFactorA					Integer32,
		upsApm160snmp_1086_InputSource1PowerFactorB					Integer32,
		upsApm160snmp_1087_InputSource1PowerFactorC					Integer32,
		upsApm160snmp_1088_InputSource1LineVoltageA					Integer32,
		upsApm160snmp_1089_InputSource1LineVoltageB					Integer32,
		upsApm160snmp_1090_InputSource1LineVoltageC					Integer32,
		upsApm160snmp_1091_InputSource1PhaseVoltageA					Integer32,
		upsApm160snmp_1092_InputSource1PhaseVoltageB					Integer32,
		upsApm160snmp_1093_InputSource1PhaseVoltageC					Integer32,
		upsApm160snmp_1094_InputSource1FrequencyA					Integer32,
		upsApm160snmp_1095_InputSource1FrequencyB					Integer32,
		upsApm160snmp_1096_InputSource1FrequencyC					Integer32,
		upsApm160snmp_1097_InputSource1THDuA					Integer32,
		upsApm160snmp_1098_InputSource1THDuB					Integer32,
		upsApm160snmp_1099_InputSource1THDuC					Integer32,
		upsApm160snmp_1100_InputSource2CurrentA					Integer32,
		upsApm160snmp_1101_InputSource2CurrentB					Integer32,
		upsApm160snmp_1102_InputSource2CurrentC					Integer32,
		upsApm160snmp_1103_InputSource2EnergyA					Integer32,
		upsApm160snmp_1104_InputSource2EnergyB					Integer32,
		upsApm160snmp_1105_InputSource2EnergyC					Integer32,
		upsApm160snmp_1106_InputSource2SwitchStatusA					INTEGER,
		upsApm160snmp_1107_InputSource2SwitchStatusB					INTEGER,
		upsApm160snmp_1108_InputSource2SwitchStatusC					INTEGER,
		upsApm160snmp_1109_InputSource2ActivePowerA					Integer32,
		upsApm160snmp_1110_InputSource2ActivePowerB					Integer32,
		upsApm160snmp_1111_InputSource2ActivePowerC					Integer32,
		upsApm160snmp_1112_InputSource2ApparentPowerA					Integer32,
		upsApm160snmp_1113_InputSource2ApparentPowerB					Integer32,
		upsApm160snmp_1114_InputSource2ApparentPowerC					Integer32,
		upsApm160snmp_1115_InputSource2THDiA					Integer32,
		upsApm160snmp_1116_InputSource2THDiB					Integer32,
		upsApm160snmp_1117_InputSource2THDiC					Integer32,
		upsApm160snmp_1118_InputSource2RatedCurrentA					Integer32,
		upsApm160snmp_1119_InputSource2RatedCurrentB					Integer32,
		upsApm160snmp_1120_InputSource2RatedCurrentC					Integer32,
		upsApm160snmp_1121_InputSource2LoadRatioA					Integer32,
		upsApm160snmp_1122_InputSource2LoadRatioB					Integer32,
		upsApm160snmp_1123_InputSource2LoadRatioC					Integer32,
		upsApm160snmp_1124_InputSource2PowerFactorA					Integer32,
		upsApm160snmp_1125_InputSource2PowerFactorB					Integer32,
		upsApm160snmp_1126_InputSource2PowerFactorC					Integer32,
		upsApm160snmp_1127_InputSource2LineVoltageA					Integer32,
		upsApm160snmp_1128_InputSource2LineVoltageB					Integer32,
		upsApm160snmp_1129_InputSource2LineVoltageC					Integer32,
		upsApm160snmp_1130_InputSource2PhaseVoltageA					Integer32,
		upsApm160snmp_1131_InputSource2PhaseVoltageB					Integer32,
		upsApm160snmp_1132_InputSource2PhaseVoltageC					Integer32,
		upsApm160snmp_1133_InputSource2FrequencyA					Integer32,
		upsApm160snmp_1134_InputSource2FrequencyB					Integer32,
		upsApm160snmp_1135_InputSource2FrequencyC					Integer32,
		upsApm160snmp_1136_InputSource2THDuA					Integer32,
		upsApm160snmp_1137_InputSource2THDuB					Integer32,
		upsApm160snmp_1138_InputSource2THDuC					Integer32,
		upsApm160snmp_1139_OnputSource1CurrentA					Integer32,
		upsApm160snmp_1140_OnputSource1CurrentB					Integer32,
		upsApm160snmp_1141_OnputSource1CurrentC					Integer32,
		upsApm160snmp_1142_OnputSource1EnergyA					Integer32,
		upsApm160snmp_1143_OnputSource1EnergyB					Integer32,
		upsApm160snmp_1144_OnputSource1EnergyC					Integer32,
		upsApm160snmp_1145_OnputSource1SwitchStatusA					INTEGER,
		upsApm160snmp_1146_OnputSource1SwitchStatusB					INTEGER,
		upsApm160snmp_1147_OnputSource1SwitchStatusC					INTEGER,
		upsApm160snmp_1148_OnputSource1ActivePowerA					Integer32,
		upsApm160snmp_1149_OnputSource1ActivePowerB					Integer32,
		upsApm160snmp_1150_OnputSource1ActivePowerC					Integer32,
		upsApm160snmp_1151_OnputSource1ApparentPowerA					Integer32,
		upsApm160snmp_1152_OnputSource1ApparentPowerB					Integer32,
		upsApm160snmp_1153_OnputSource1ApparentPowerC					Integer32,
		upsApm160snmp_1154_OnputSource1THDiA					Integer32,
		upsApm160snmp_1155_OnputSource1THDiB					Integer32,
		upsApm160snmp_1156_OnputSource1THDiC					Integer32,
		upsApm160snmp_1157_OnputSource1RatedCurrentA					Integer32,
		upsApm160snmp_1158_OnputSource1RatedCurrentB					Integer32,
		upsApm160snmp_1159_OnputSource1RatedCurrentC					Integer32,
		upsApm160snmp_1160_OnputSource1LoadRatioA					Integer32,
		upsApm160snmp_1161_OnputSource1LoadRatioB					Integer32,
		upsApm160snmp_1162_OnputSource1LoadRatioC					Integer32,
		upsApm160snmp_1163_OnputSource1PowerFactorA					Integer32,
		upsApm160snmp_1164_OnputSource1PowerFactorB					Integer32,
		upsApm160snmp_1165_OnputSource1PowerFactorC					Integer32,
		upsApm160snmp_1166_OnputSource1LineVoltageA					Integer32,
		upsApm160snmp_1167_OnputSource1LineVoltageB					Integer32,
		upsApm160snmp_1168_OnputSource1LineVoltageC					Integer32,
		upsApm160snmp_1169_OnputSource1PhaseVoltageA					Integer32,
		upsApm160snmp_1170_OnputSource1PhaseVoltageB					Integer32,
		upsApm160snmp_1171_OnputSource1PhaseVoltageC					Integer32,
		upsApm160snmp_1172_OnputSource1FrequencyA					Integer32,
		upsApm160snmp_1173_OnputSource1FrequencyB					Integer32,
		upsApm160snmp_1174_OnputSource1FrequencyC					Integer32,
		upsApm160snmp_1175_OnputSource1THDuA					Integer32,
		upsApm160snmp_1176_OnputSource1THDuB					Integer32,
		upsApm160snmp_1177_OnputSource1THDuC					Integer32,
		upsApm160snmp_1178_UPSCommunicationInterrupt					INTEGER,
		upsApm160snmp_1179_UPSCommunicationInterruptRec					INTEGER,
		upsApm160snmp_1180_UPSNoOutput					INTEGER,
		upsApm160snmp_1181_UPSOnBypass					INTEGER,
		upsApm160snmp_1182_UPSinNormalMode					INTEGER,
		upsApm160snmp_1183_UPSinBatteryMode					INTEGER,
		upsApm160snmp_1184_BatteryTestInitiated					INTEGER,
		upsApm160snmp_1185_BatteryNotInTesting					INTEGER,
		upsApm160snmp_1186_BatteryFloatCharging					INTEGER,
		upsApm160snmp_1187_BatteryBoostCharging					INTEGER,
		upsApm160snmp_1188_BatteryNotInCharging					INTEGER,
		upsApm160snmp_1189_UPSInverterOff					INTEGER,
		upsApm160snmp_1190_UPSInverterOn					INTEGER,
		upsApm160snmp_1191_OnGenerator					INTEGER,
		upsApm160snmp_1192_NotOnGenerator					INTEGER,
		upsApm160snmp_1193_InputSwitchOpen					INTEGER,
		upsApm160snmp_1194_InputSwitchClosed					INTEGER,
		upsApm160snmp_1195_MaintainenceSwitchOpen					INTEGER,
		upsApm160snmp_1196_MaintainenceSwitchClosed					INTEGER,
		upsApm160snmp_1197_BypassSwitchOpen					INTEGER,
		upsApm160snmp_1198_BypassSwitchClosed					INTEGER,
		upsApm160snmp_1199_OutputSwitchOpen					INTEGER,
		upsApm160snmp_1200_OutputSwitchClosed					INTEGER,
		upsApm160snmp_1201_ExternalMaintanceswitchOpen					INTEGER,
		upsApm160snmp_1202_ExternalMaintanceswitchClose					INTEGER,
		upsApm160snmp_1203_ExternalOutputswitchOpen					INTEGER,
		upsApm160snmp_1204_ExternalOutputswitchClosed					INTEGER,
		upsApm160snmp_1205_ExternalMaintIsolationswitc					INTEGER,
		upsApm160snmp_1206_ExternalMaintIsolationswitc					INTEGER,
		upsApm160snmp_1207_BCBAbsent					INTEGER,
		upsApm160snmp_1208_BCBClosed					INTEGER,
		upsApm160snmp_1209_BCBOpen					INTEGER,
		upsApm160snmp_1210_ModuleRunning					INTEGER,
		upsApm160snmp_1211_ModuleSleeping					INTEGER,
		upsApm160snmp_1212_InverterAsynchronousRecovered					INTEGER,
		upsApm160snmp_1213_InverterAsynchronous					INTEGER,
		upsApm160snmp_1214_InputVoltageAbnormalRecovere					INTEGER,
		upsApm160snmp_1215_InputVoltageAbnormal					INTEGER,
		upsApm160snmp_1216_RectifierFaultRecovered					INTEGER,
		upsApm160snmp_1217_RectifierFault					INTEGER,
		upsApm160snmp_1218_InverterFaultRecovered					INTEGER,
		upsApm160snmp_1219_InverterFault					INTEGER,
		upsApm160snmp_1220_BypassAbnormalRecovered					INTEGER,
		upsApm160snmp_1221_BypassAbnormal					INTEGER,
		upsApm160snmp_1222_BatteryNormal					INTEGER,
		upsApm160snmp_1223_BatteryUndervoltage					INTEGER,
		upsApm160snmp_1224_BatteryOvervoltage					INTEGER,
		upsApm160snmp_1225_NoBattery					INTEGER,
		upsApm160snmp_1226_LowBatteryWarning					INTEGER,
		upsApm160snmp_1227_BatteryReversed					INTEGER,
		upsApm160snmp_1228_AmbientOvertemperatureRecover					INTEGER,
		upsApm160snmp_1229_AmbientOvertemperatureRecover					INTEGER,
		upsApm160snmp_1230_PowerCANCommunicationnormal					INTEGER,
		upsApm160snmp_1231_PowerCANCommunicationAbnormal					INTEGER,
		upsApm160snmp_1232_RecDSPSWErrorRecovered					INTEGER,
		upsApm160snmp_1233_RecDSPSWError					INTEGER,
		upsApm160snmp_1234_OutputDisabledRecovered					INTEGER,
		upsApm160snmp_1235_OutputDisabled					INTEGER,
		upsApm160snmp_1236_InverterDSPSoftwareErrorRec					INTEGER,
		upsApm160snmp_1237_InverterDSPSoftwareError					INTEGER,
		upsApm160snmp_1238_InverterFPGASoftwareErrorRe					INTEGER,
		upsApm160snmp_1239_InverterFPGASoftwareError					INTEGER,
		upsApm160snmp_1240_BypassDSPSoftwareErrorRecov					INTEGER,
		upsApm160snmp_1241_BypassDSPSoftwareError					INTEGER,
		upsApm160snmp_1242_BypassFPGASoftwareErrorReco					INTEGER,
		upsApm160snmp_1243_BypassFPGASoftwareError					INTEGER,
		upsApm160snmp_1244_DiscreteBusCommunicationNorm					INTEGER,
		upsApm160snmp_1245_DiscreteBusCommunicationAbno					INTEGER,
		upsApm160snmp_1246_LBSAbnormalRecovered					INTEGER,
		upsApm160snmp_1247_LBSAbnormal					INTEGER,
		upsApm160snmp_1248_EPORecovered					INTEGER,
		upsApm160snmp_1249_EPO					INTEGER,
		upsApm160snmp_1250_BypassSTSFailRecovered					INTEGER,
		upsApm160snmp_1251_BypassSTSFail					INTEGER,
		upsApm160snmp_1252_BypassPhaseReversedRecovered					INTEGER,
		upsApm160snmp_1253_BypassPhaseReversed					INTEGER,
		upsApm160snmp_1254_BypassOvercurrentRecovered					INTEGER,
		upsApm160snmp_1255_BypassOvercurrent					INTEGER,
		upsApm160snmp_1256_BypassAbnormalShutdownRecove					INTEGER,
		upsApm160snmp_1257_BypassAbnormalShutdown					INTEGER,
		upsApm160snmp_1258_ExcessAutoRexfersRecovered					INTEGER,
		upsApm160snmp_1259_ExcessAutoRexfers					INTEGER,
		upsApm160snmp_1260_ExcessECOAutoXfersRecovered					INTEGER,
		upsApm160snmp_1261_ExcessECOAutoXfers					INTEGER,
		upsApm160snmp_1262_ParaPowerCANCommunicationAbno					INTEGER,
		upsApm160snmp_1263_ParaPowerCANCommunicationAbno					INTEGER,
		upsApm160snmp_1264_DischargerCurrentLimitRecove					INTEGER,
		upsApm160snmp_1265_DischargerCurrentLimit					INTEGER,
		upsApm160snmp_1266_DischargerFaultRecovered					INTEGER,
		upsApm160snmp_1267_DischargerFault					INTEGER,
		upsApm160snmp_1268_ChargerFaultRecovered					INTEGER,
		upsApm160snmp_1269_ChargerFault					INTEGER,
		upsApm160snmp_1270_LBSCableAbnormalRecovered					INTEGER,
		upsApm160snmp_1271_LBSCableAbnormal					INTEGER,
		upsApm160snmp_1272_BatteryMaintainRecovered					INTEGER,
		upsApm160snmp_1273_BatteryMaintain					INTEGER,
		upsApm160snmp_1274_BatteryOvertemperatureRecover					INTEGER,
		upsApm160snmp_1275_BatteryOvertemperature					INTEGER,
		upsApm160snmp_1276_BatteryGroundFaultRecovered					INTEGER,
		upsApm160snmp_1277_BatteryGroundFault					INTEGER,
		upsApm160snmp_1278_InputFrequencyAbnormalRecove					INTEGER,
		upsApm160snmp_1279_InputFrequencyAbnormal					INTEGER,
		upsApm160snmp_1280_ModuleOvertemperatureRecovere					INTEGER,
		upsApm160snmp_1281_ModuleOvertemperature					INTEGER,
		upsApm160snmp_1282_InputTransformerOvertempReco					INTEGER,
		upsApm160snmp_1283_InputTransformerOvertemperatu					INTEGER,
		upsApm160snmp_1284_BypassTransformerOvertempRec					INTEGER,
		upsApm160snmp_1285_BypassTransformerOvertemperat					INTEGER,
		upsApm160snmp_1286_EqualizeChargeTimeoutRecover					INTEGER,
		upsApm160snmp_1287_EqualizeChargeTimeout					INTEGER,
		upsApm160snmp_1288_ControlPowerFailRecovered					INTEGER,
		upsApm160snmp_1289_ControlPowerFail					INTEGER,
		upsApm160snmp_1290_InputPhaseReversedRecovered					INTEGER,
		upsApm160snmp_1291_InputPhaseReversed					INTEGER,
		upsApm160snmp_1292_RectifierSoftStartFailRecov					INTEGER,
		upsApm160snmp_1293_RectifierSoftStartFail					INTEGER,
		upsApm160snmp_1294_OperationInvalidRecovered					INTEGER,
		upsApm160snmp_1295_OperationInvalid					INTEGER,
		upsApm160snmp_1296_OutputOverloadRecovered					INTEGER,
		upsApm160snmp_1297_OutputOverload					INTEGER,
		upsApm160snmp_1298_MMSCapacityExceededRecovered					INTEGER,
		upsApm160snmp_1299_MMSCapacityExceeded					INTEGER,
		upsApm160snmp_1300_OutputOverloadTimeoutRecover					INTEGER,
		upsApm160snmp_1301_OutputOverloadTimeout					INTEGER,
		upsApm160snmp_1302_LoadImpactTransferRecovered					INTEGER,
		upsApm160snmp_1303_LoadImpactTransfer					INTEGER,
		upsApm160snmp_1304_LoadSharingAbnormalRecovered					INTEGER,
		upsApm160snmp_1305_LoadSharingAbnormal					INTEGER,
		upsApm160snmp_1306_DCBusAbnormalShutdownRecove					INTEGER,
		upsApm160snmp_1307_DCBusAbnormalShutdown					INTEGER,
		upsApm160snmp_1308_OtherModuleXferRecovered					INTEGER,
		upsApm160snmp_1309_OtherModuleXfer					INTEGER,
		upsApm160snmp_1310_DCBusOvervoltageRecovered					INTEGER,
		upsApm160snmp_1311_DCBusOvervoltage					INTEGER,
		upsApm160snmp_1312_MonCANCommunicationAbnormalR					INTEGER,
		upsApm160snmp_1313_MonCANCommunicationAbnormal					INTEGER,
		upsApm160snmp_1314_InputNeutralLostRecovered					INTEGER,
		upsApm160snmp_1315_InputNeutralLost					INTEGER,
		upsApm160snmp_1316_InverterRelayFailRecovered					INTEGER,
		upsApm160snmp_1317_InverterRelayFail					INTEGER,
		upsApm160snmp_1318_InputBackfeedRecovered					INTEGER,
		upsApm160snmp_1319_InputBackfeed					INTEGER,
		upsApm160snmp_1320_InputCurrentAbnormalRecovere					INTEGER,
		upsApm160snmp_1321_InputCurrentAbnormal					INTEGER,
		upsApm160snmp_1322_OutputVoltageAbnormalRecover					INTEGER,
		upsApm160snmp_1323_OutputVoltageAbnormal					INTEGER,
		upsApm160snmp_1324_InputCurrentLimitRecovered					INTEGER,
		upsApm160snmp_1325_InputCurrentLimit					INTEGER,
		upsApm160snmp_1326_BypassOvertemperature					INTEGER,
		upsApm160snmp_1327_BypassOvertemperature					INTEGER,
		upsApm160snmp_1328_OtherBypassSTSFailRecovered					INTEGER,
		upsApm160snmp_1329_OtherBypassSTSFail					INTEGER,
		upsApm160snmp_1330_ParallelCableAbnormalRecover					INTEGER,
		upsApm160snmp_1331_ParallelCableAbnormal					INTEGER,
		upsApm160snmp_1332_ChargerOvertemperatureRecover					INTEGER,
		upsApm160snmp_1333_ChargerOvertemperature					INTEGER,
		upsApm160snmp_1334_BatteryTerminalShortRecovere					INTEGER,
		upsApm160snmp_1335_BatteryTerminalShort					INTEGER,
		upsApm160snmp_1336_BatteryRoomTemperatureAbnorm					INTEGER,
		upsApm160snmp_1337_BatteryRoomTemperatureAbnorm					INTEGER,
		upsApm160snmp_1338_FanAbnormalRecovered					INTEGER,
		upsApm160snmp_1339_FanAbnormal					INTEGER,
		upsApm160snmp_1340_BypassinChargeRecovered					INTEGER,
		upsApm160snmp_1341_BypassinCharge					INTEGER,
		upsApm160snmp_1342_BCBStatusAbnormalRecovered					INTEGER,
		upsApm160snmp_1343_BCBStatusAbnormal					INTEGER,
		upsApm160snmp_1344_BypassModuleUnauthorizedReco					INTEGER,
		upsApm160snmp_1345_BypassModuleUnauthorized					INTEGER,
		upsApm160snmp_1346_PowerModuleUnauthorizedRecov					INTEGER,
		upsApm160snmp_1347_PowerModuleUnauthorized					INTEGER,
		upsApm160snmp_1348_HMIUnauthorizedRecovered					INTEGER,
		upsApm160snmp_1349_HMIUnauthorized					INTEGER,
		upsApm160snmp_1350_BypassSCRFanAbnormalRecover					INTEGER,
		upsApm160snmp_1351_BypassSCRFanAbnormal					INTEGER,
		upsApm160snmp_1352_BalancerFaultRecovered					INTEGER,
		upsApm160snmp_1353_BalancerFault					INTEGER,
		upsApm160snmp_1354_BalancerOvercurrentRecovered					INTEGER,
		upsApm160snmp_1355_BalancerOvercurrent					INTEGER,
		upsApm160snmp_1356_BalancerOvertemperatureRecove					INTEGER,
		upsApm160snmp_1357_BalancerOvertemperature					INTEGER,
		upsApm160snmp_1358_LossofRedundancyRecovered					INTEGER,
		upsApm160snmp_1359_LossofRedundancy					INTEGER,
		upsApm160snmp_1360_PowerHardwareMismatchRecover					INTEGER,
		upsApm160snmp_1361_PowerHardwareMismatch					INTEGER,
		upsApm160snmp_1362_ModuleNotReadyRecovered					INTEGER,
		upsApm160snmp_1363_ModuleNotReady					INTEGER,
		upsApm160snmp_1364_TopoutletFanAbnormalRecover					INTEGER,
		upsApm160snmp_1365_TopoutletFanAbnormal					INTEGER,
		upsApm160snmp_1366_PhaseAOutputFuseFailRecove					INTEGER,
		upsApm160snmp_1367_PhaseAOutputFuseFail					INTEGER,
		upsApm160snmp_1368_PhaseBOutputFuseFailRecove					INTEGER,
		upsApm160snmp_1369_PhaseBOutputFuseFail					INTEGER,
		upsApm160snmp_1370_PhaseCOutputFuseFailRecove					INTEGER,
		upsApm160snmp_1371_PhaseCOutputFuseFail					INTEGER,
		upsApm160snmp_1372_ParameterConfigurationFailRe					INTEGER,
		upsApm160snmp_1373_ParameterConfigurationFail					INTEGER,
		upsApm160snmp_1374_BypassOvercurrentTimeoutReco					INTEGER,
		upsApm160snmp_1375_BypassOvercurrentTimeout					INTEGER,
		upsApm160snmp_1376_OvervoltageNGNDRecovered					INTEGER,
		upsApm160snmp_1377_OvervoltageNGND					INTEGER,
		upsApm160snmp_1378_BypassNotAvailableRecovered					INTEGER,
		upsApm160snmp_1379_BypassNotAvailable					INTEGER,
		upsApm160snmp_1380_OutputTransformerOvertemperat					INTEGER,
		upsApm160snmp_1381_OutputTransformerOvertemperat					INTEGER,
		upsApm160snmp_1382_OutputFuseFailRecovered					INTEGER,
		upsApm160snmp_1383_OutputFuseFail					INTEGER,
		upsApm160snmp_1384_BatteryTestFailRecovered					INTEGER,
		upsApm160snmp_1385_BatteryTestFail					INTEGER,
		upsApm160snmp_1386_LoadShedSignal1NotActive					INTEGER,
		upsApm160snmp_1387_LoadShedSignal1Active					INTEGER,
		upsApm160snmp_1388_LoadShedSignal2NotActive					INTEGER,
		upsApm160snmp_1389_LoadShedSignal2Active					INTEGER,
		upsApm160snmp_1390_BypassModuleAvailable					INTEGER,
		upsApm160snmp_1391_BypassModuleNotAvailable					INTEGER,
		upsApm160snmp_1392_ControlModuleAvailable					INTEGER,
		upsApm160snmp_1393_ControlModuleNotAvailable					INTEGER,
		upsApm160snmp_1394_SystemMainsFuseNormal					INTEGER,
		upsApm160snmp_1395_SystemMainsFuseFail					INTEGER,
		upsApm160snmp_1396_BypassFuseNormal					INTEGER,
		upsApm160snmp_1397_BypassFuseFail					INTEGER,
		upsApm160snmp_1398_SystemOutputFuseNormal					INTEGER,
		upsApm160snmp_1399_SystemOutputFuseFail					INTEGER,
		upsApm160snmp_1400_LoadonMaintainaceBypassNorm					INTEGER,
		upsApm160snmp_1401_LoadonMaintainaceBypass					INTEGER,
		upsApm160snmp_1402_Outputnormal					INTEGER,
		upsApm160snmp_1403_Outputshort					INTEGER,
		upsApm160snmp_1404_Batterynormal					INTEGER,
		upsApm160snmp_1405_BatteryDeepDischargeAlarm					INTEGER,
		upsApm160snmp_1406_LoadonBypassUnionRecovered					INTEGER,
		upsApm160snmp_1407_LoadonBypassUnion					INTEGER,
		upsApm160snmp_1408_SPMInternalCommFailureRecov					INTEGER,
		upsApm160snmp_1409_SPMInternalCommFailure					INTEGER,
		upsApm160snmp_1410_SPD1BreakerOpenRecovered					INTEGER,
		upsApm160snmp_1411_SPD1BreakerOpen					INTEGER,
		upsApm160snmp_1412_SPD1OpenRecovered					INTEGER,
		upsApm160snmp_1413_SPD1Open					INTEGER,
		upsApm160snmp_1414_SPD2BreakerOpenRecovered					INTEGER,
		upsApm160snmp_1415_SPD2BreakerOpen					INTEGER,
		upsApm160snmp_1416_SPD2OpenRecovered					INTEGER,
		upsApm160snmp_1417_SPD2Open					INTEGER,
		upsApm160snmp_1418_Board1Ready					INTEGER,
		upsApm160snmp_1419_Board1NotReady					INTEGER,
		upsApm160snmp_1420_Board2Ready					INTEGER,
		upsApm160snmp_1421_Board2NotReady					INTEGER,
		upsApm160snmp_1422_Board3Ready					INTEGER,
		upsApm160snmp_1423_Board3NotReady					INTEGER,
		upsApm160snmp_1424_Board4Ready					INTEGER,
		upsApm160snmp_1425_Board4NotReady					INTEGER,
		upsApm160snmp_1426_Board5Ready					INTEGER,
		upsApm160snmp_1427_Board5NotReady					INTEGER,
		upsApm160snmp_1428_Board6Ready					INTEGER,
		upsApm160snmp_1429_Board6NotReady					INTEGER,
		upsApm160snmp_1430_Board7Ready					INTEGER,
		upsApm160snmp_1431_Board7NotReady					INTEGER,
		upsApm160snmp_1432_Board8Ready					INTEGER,
		upsApm160snmp_1433_Board8NotReady					INTEGER,
		upsApm160snmp_1434_Board9Ready					INTEGER,
		upsApm160snmp_1435_Board9NotReady					INTEGER,
		upsApm160snmp_1436_Board10Ready					INTEGER,
		upsApm160snmp_1437_Board10NotReady					INTEGER,
		upsApm160snmp_1438_Board11Ready					INTEGER,
		upsApm160snmp_1439_Board11NotReady					INTEGER,
		upsApm160snmp_1440_Board12Ready					INTEGER,
		upsApm160snmp_1441_Board12NotReady					INTEGER,
		upsApm160snmp_1442_Board13Ready					INTEGER,
		upsApm160snmp_1443_Board13NotReady					INTEGER,
		upsApm160snmp_1444_Board14Ready					INTEGER,
		upsApm160snmp_1445_Board14NotReady					INTEGER,
		upsApm160snmp_1446_Board15Ready					INTEGER,
		upsApm160snmp_1447_Board15NotReady					INTEGER,
		upsApm160snmp_1448_Board16Ready					INTEGER,
		upsApm160snmp_1449_Board16NotReady					INTEGER,
		upsApm160snmp_1450_SPMCRCCheckErrorRecovered					INTEGER,
		upsApm160snmp_1451_SPMCRCCheckError					INTEGER,
		upsApm160snmp_1452_ExternalInputSwitchRecovered					INTEGER,
		upsApm160snmp_1453_ExternalInputSwitchOpen					INTEGER,
		upsApm160snmp_1454_ExternalBypassSwitchRecovere					INTEGER,
		upsApm160snmp_1455_ExternalBypassSwitchOpen					INTEGER,
		upsApm160snmp_1456_BranchOverCurrent					INTEGER,
		upsApm160snmp_1457_BranchCurrentOverHighLimit					INTEGER,
		upsApm160snmp_1458_BranchCurrentOverLowLimit					INTEGER,
		upsApm160snmp_1459_BranchInrushOverCurrent					INTEGER,
		upsApm160snmp_1460_BranchBreakerFail					INTEGER,
		upsApm160snmp_1461_ParaDiscreteBusCommunicatonN					INTEGER,
		upsApm160snmp_1462_ParaDiscreteBusCommunicatonA					INTEGER,
		upsApm160snmp_1463_CommunicateStatus					INTEGER }
upsApm160snmpIndex OBJECT-TYPE
		SYNTAX Integer32(1..1463)
		MAX-ACCESS read-only
		STATUS current
		DESCRIPTION
		"upsApm160snmp System Entry Index."
		::= { upsApm160snmpEntry 1 }
upsApm160snmp_2_systemOutputAcitvePowerA OBJECT-TYPE
		SYNTAX Integer32
		
		MAX-ACCESS read-only
		STATUS current
		DESCRIPTION
		"upsApm160snmp_2_systemOutputAcitvePowerA stored as 0.01kW."
		::= { upsApm160snmpEntry 2 }
upsApm160snmp_3_systemOutputAcitvePowerB OBJECT-TYPE
		SYNTAX Integer32
		
		MAX-ACCESS read-only
		STATUS current
		DESCRIPTION
		"upsApm160snmp_3_systemOutputAcitvePowerB stored as 0.01kW."
		::= { upsApm160snmpEntry 3 }
upsApm160snmp_4_systemOutputAcitvePowerC OBJECT-TYPE
		SYNTAX Integer32
		
		MAX-ACCESS read-only
		STATUS current
		DESCRIPTION
		"upsApm160snmp_4_systemOutputAcitvePowerC stored as 0.01kW."
		::= { upsApm160snmpEntry 4 }
upsApm160snmp_5_systemOutputAppPowerA OBJECT-TYPE
		SYNTAX Integer32
		
		MAX-ACCESS read-only
		STATUS current
		DESCRIPTION
		"upsApm160snmp_5_systemOutputAppPowerA stored as 0.01kVA."
		::= { upsApm160snmpEntry 5 }
upsApm160snmp_6_systemOutputAppPowerB OBJECT-TYPE
		SYNTAX Integer32
		
		MAX-ACCESS read-only
		STATUS current
		DESCRIPTION
		"upsApm160snmp_6_systemOutputAppPowerB stored as 0.01kVA."
		::= { upsApm160snmpEntry 6 }
upsApm160snmp_7_systemOutputAppPowerC OBJECT-TYPE
		SYNTAX Integer32
		
		MAX-ACCESS read-only
		STATUS current
		DESCRIPTION
		"upsApm160snmp_7_systemOutputAppPowerC stored as 0.01kVA."
		::= { upsApm160snmpEntry 7 }
upsApm160snmp_8_systemOutputReactivePowerA OBJECT-TYPE
		SYNTAX Integer32
		
		MAX-ACCESS read-only
		STATUS current
		DESCRIPTION
		"upsApm160snmp_8_systemOutputReactivePowerA stored as 0.01kVar."
		::= { upsApm160snmpEntry 8 }
upsApm160snmp_9_systemOutputReactivePowerB OBJECT-TYPE
		SYNTAX Integer32
		
		MAX-ACCESS read-only
		STATUS current
		DESCRIPTION
		"upsApm160snmp_9_systemOutputReactivePowerB stored as 0.01kVar."
		::= { upsApm160snmpEntry 9 }
upsApm160snmp_10_systemOutputReactivePowerC OBJECT-TYPE
		SYNTAX Integer32
		
		MAX-ACCESS read-only
		STATUS current
		DESCRIPTION
		"upsApm160snmp_10_systemOutputReactivePowerC stored as 0.01kVar."
		::= { upsApm160snmpEntry 10 }
upsApm160snmp_11_environmentTemperature OBJECT-TYPE
		SYNTAX Integer32
		
		MAX-ACCESS read-only
		STATUS current
		DESCRIPTION
		"upsApm160snmp_11_environmentTemperature stored as 0.01℃."
		::= { upsApm160snmpEntry 11 }
upsApm160snmp_12_requitsiteModules OBJECT-TYPE
		SYNTAX Integer32
		
		MAX-ACCESS read-only
		STATUS current
		DESCRIPTION
		"upsApm160snmp_12_requitsiteModules stored as 0.01."
		::= { upsApm160snmpEntry 12 }
upsApm160snmp_13_redundantModules OBJECT-TYPE
		SYNTAX Integer32
		
		MAX-ACCESS read-only
		STATUS current
		DESCRIPTION
		"upsApm160snmp_13_redundantModules stored as 0.01."
		::= { upsApm160snmpEntry 13 }
upsApm160snmp_14_unitGrantCapacity OBJECT-TYPE
		SYNTAX Integer32
		
		MAX-ACCESS read-only
		STATUS current
		DESCRIPTION
		"upsApm160snmp_14_unitGrantCapacity stored as 0.01."
		::= { upsApm160snmpEntry 14 }
upsApm160snmp_15_unitCapacity OBJECT-TYPE
		SYNTAX Integer32
		
		MAX-ACCESS read-only
		STATUS current
		DESCRIPTION
		"upsApm160snmp_15_unitCapacity stored as 0.01."
		::= { upsApm160snmpEntry 15 }
upsApm160snmp_16_ModuleinputPhaseVoltageA OBJECT-TYPE
		SYNTAX Integer32
		
		MAX-ACCESS read-only
		STATUS current
		DESCRIPTION
		"upsApm160snmp_16_ModuleinputPhaseVoltageA stored as 0.01V."
		::= { upsApm160snmpEntry 16 }
upsApm160snmp_17_ModuleinputPhaseVoltageB OBJECT-TYPE
		SYNTAX Integer32
		
		MAX-ACCESS read-only
		STATUS current
		DESCRIPTION
		"upsApm160snmp_17_ModuleinputPhaseVoltageB stored as 0.01V."
		::= { upsApm160snmpEntry 17 }
upsApm160snmp_18_ModuleinputPhaseVoltageC OBJECT-TYPE
		SYNTAX Integer32
		
		MAX-ACCESS read-only
		STATUS current
		DESCRIPTION
		"upsApm160snmp_18_ModuleinputPhaseVoltageC stored as 0.01V."
		::= { upsApm160snmpEntry 18 }
upsApm160snmp_19_ModuleinputLineVoltageA OBJECT-TYPE
		SYNTAX Integer32
		
		MAX-ACCESS read-only
		STATUS current
		DESCRIPTION
		"upsApm160snmp_19_ModuleinputLineVoltageA stored as 0.01V."
		::= { upsApm160snmpEntry 19 }
upsApm160snmp_20_ModuleinputLineVoltageB OBJECT-TYPE
		SYNTAX Integer32
		
		MAX-ACCESS read-only
		STATUS current
		DESCRIPTION
		"upsApm160snmp_20_ModuleinputLineVoltageB stored as 0.01V."
		::= { upsApm160snmpEntry 20 }
upsApm160snmp_21_ModuleinputLineVoltageC OBJECT-TYPE
		SYNTAX Integer32
		
		MAX-ACCESS read-only
		STATUS current
		DESCRIPTION
		"upsApm160snmp_21_ModuleinputLineVoltageC stored as 0.01V."
		::= { upsApm160snmpEntry 21 }
upsApm160snmp_22_ModuleinputCurrentA OBJECT-TYPE
		SYNTAX Integer32
		
		MAX-ACCESS read-only
		STATUS current
		DESCRIPTION
		"upsApm160snmp_22_ModuleinputCurrentA stored as 0.01A."
		::= { upsApm160snmpEntry 22 }
upsApm160snmp_23_ModuleinputCurrentB OBJECT-TYPE
		SYNTAX Integer32
		
		MAX-ACCESS read-only
		STATUS current
		DESCRIPTION
		"upsApm160snmp_23_ModuleinputCurrentB stored as 0.01A."
		::= { upsApm160snmpEntry 23 }
upsApm160snmp_24_ModuleinputCurrentC OBJECT-TYPE
		SYNTAX Integer32
		
		MAX-ACCESS read-only
		STATUS current
		DESCRIPTION
		"upsApm160snmp_24_ModuleinputCurrentC stored as 0.01A."
		::= { upsApm160snmpEntry 24 }
upsApm160snmp_25_ModuleinputFrequency OBJECT-TYPE
		SYNTAX Integer32
		
		MAX-ACCESS read-only
		STATUS current
		DESCRIPTION
		"upsApm160snmp_25_ModuleinputFrequency stored as 0.01Hz."
		::= { upsApm160snmpEntry 25 }
upsApm160snmp_26_ModuleinputPowerFactorA OBJECT-TYPE
		SYNTAX Integer32
		
		MAX-ACCESS read-only
		STATUS current
		DESCRIPTION
		"upsApm160snmp_26_ModuleinputPowerFactorA stored as 0.01."
		::= { upsApm160snmpEntry 26 }
upsApm160snmp_27_ModuleinputPowerFactorB OBJECT-TYPE
		SYNTAX Integer32
		
		MAX-ACCESS read-only
		STATUS current
		DESCRIPTION
		"upsApm160snmp_27_ModuleinputPowerFactorB stored as 0.01."
		::= { upsApm160snmpEntry 27 }
upsApm160snmp_28_ModuleinputPowerFactorC OBJECT-TYPE
		SYNTAX Integer32
		
		MAX-ACCESS read-only
		STATUS current
		DESCRIPTION
		"upsApm160snmp_28_ModuleinputPowerFactorC stored as 0.01."
		::= { upsApm160snmpEntry 28 }
upsApm160snmp_29_ModulebatteryVoltage OBJECT-TYPE
		SYNTAX Integer32
		
		MAX-ACCESS read-only
		STATUS current
		DESCRIPTION
		"upsApm160snmp_29_ModulebatteryVoltage stored as 0.01V."
		::= { upsApm160snmpEntry 29 }
upsApm160snmp_30_ModuleinputActivePowerA OBJECT-TYPE
		SYNTAX Integer32
		
		MAX-ACCESS read-only
		STATUS current
		DESCRIPTION
		"upsApm160snmp_30_ModuleinputActivePowerA stored as 0.01kW."
		::= { upsApm160snmpEntry 30 }
upsApm160snmp_31_ModuleinputActivePowerB OBJECT-TYPE
		SYNTAX Integer32
		
		MAX-ACCESS read-only
		STATUS current
		DESCRIPTION
		"upsApm160snmp_31_ModuleinputActivePowerB stored as 0.01kW."
		::= { upsApm160snmpEntry 31 }
upsApm160snmp_32_ModuleinputActivePowerC OBJECT-TYPE
		SYNTAX Integer32
		
		MAX-ACCESS read-only
		STATUS current
		DESCRIPTION
		"upsApm160snmp_32_ModuleinputActivePowerC stored as 0.01kW."
		::= { upsApm160snmpEntry 32 }
upsApm160snmp_33_ModuleinputAppPowerA OBJECT-TYPE
		SYNTAX Integer32
		
		MAX-ACCESS read-only
		STATUS current
		DESCRIPTION
		"upsApm160snmp_33_ModuleinputAppPowerA stored as 0.01kVA."
		::= { upsApm160snmpEntry 33 }
upsApm160snmp_34_ModuleinputAppPowerB OBJECT-TYPE
		SYNTAX Integer32
		
		MAX-ACCESS read-only
		STATUS current
		DESCRIPTION
		"upsApm160snmp_34_ModuleinputAppPowerB stored as 0.01kVA."
		::= { upsApm160snmpEntry 34 }
upsApm160snmp_35_ModuleinputAppPowerC OBJECT-TYPE
		SYNTAX Integer32
		
		MAX-ACCESS read-only
		STATUS current
		DESCRIPTION
		"upsApm160snmp_35_ModuleinputAppPowerC stored as 0.01kVA."
		::= { upsApm160snmpEntry 35 }
upsApm160snmp_36_ModuleinputEnergyA OBJECT-TYPE
		SYNTAX Integer32
		
		MAX-ACCESS read-only
		STATUS current
		DESCRIPTION
		"upsApm160snmp_36_ModuleinputEnergyA stored as 0.01kWh."
		::= { upsApm160snmpEntry 36 }
upsApm160snmp_37_ModuleinputEnergyB OBJECT-TYPE
		SYNTAX Integer32
		
		MAX-ACCESS read-only
		STATUS current
		DESCRIPTION
		"upsApm160snmp_37_ModuleinputEnergyB stored as 0.01kWh."
		::= { upsApm160snmpEntry 37 }
upsApm160snmp_38_ModuleinputEnergyC OBJECT-TYPE
		SYNTAX Integer32
		
		MAX-ACCESS read-only
		STATUS current
		DESCRIPTION
		"upsApm160snmp_38_ModuleinputEnergyC stored as 0.01kWh."
		::= { upsApm160snmpEntry 38 }
upsApm160snmp_39_ModuleoutputVoltageA OBJECT-TYPE
		SYNTAX Integer32
		
		MAX-ACCESS read-only
		STATUS current
		DESCRIPTION
		"upsApm160snmp_39_ModuleoutputVoltageA stored as 0.01V."
		::= { upsApm160snmpEntry 39 }
upsApm160snmp_40_ModuleoutputVoltageB OBJECT-TYPE
		SYNTAX Integer32
		
		MAX-ACCESS read-only
		STATUS current
		DESCRIPTION
		"upsApm160snmp_40_ModuleoutputVoltageB stored as 0.01V."
		::= { upsApm160snmpEntry 40 }
upsApm160snmp_41_ModuleoutputVoltageC OBJECT-TYPE
		SYNTAX Integer32
		
		MAX-ACCESS read-only
		STATUS current
		DESCRIPTION
		"upsApm160snmp_41_ModuleoutputVoltageC stored as 0.01V."
		::= { upsApm160snmpEntry 41 }
upsApm160snmp_42_ModuleoutputLineVoltageAB OBJECT-TYPE
		SYNTAX Integer32
		
		MAX-ACCESS read-only
		STATUS current
		DESCRIPTION
		"upsApm160snmp_42_ModuleoutputLineVoltageAB stored as 0.01V."
		::= { upsApm160snmpEntry 42 }
upsApm160snmp_43_ModuleoutputLineVoltageBC OBJECT-TYPE
		SYNTAX Integer32
		
		MAX-ACCESS read-only
		STATUS current
		DESCRIPTION
		"upsApm160snmp_43_ModuleoutputLineVoltageBC stored as 0.01V."
		::= { upsApm160snmpEntry 43 }
upsApm160snmp_44_ModuleoutputLineVoltageCA OBJECT-TYPE
		SYNTAX Integer32
		
		MAX-ACCESS read-only
		STATUS current
		DESCRIPTION
		"upsApm160snmp_44_ModuleoutputLineVoltageCA stored as 0.01V."
		::= { upsApm160snmpEntry 44 }
upsApm160snmp_45_ModuleoutputCurrentA OBJECT-TYPE
		SYNTAX Integer32
		
		MAX-ACCESS read-only
		STATUS current
		DESCRIPTION
		"upsApm160snmp_45_ModuleoutputCurrentA stored as 0.01A."
		::= { upsApm160snmpEntry 45 }
upsApm160snmp_46_ModuleoutputCurrentB OBJECT-TYPE
		SYNTAX Integer32
		
		MAX-ACCESS read-only
		STATUS current
		DESCRIPTION
		"upsApm160snmp_46_ModuleoutputCurrentB stored as 0.01A."
		::= { upsApm160snmpEntry 46 }
upsApm160snmp_47_ModuleoutputCurrentC OBJECT-TYPE
		SYNTAX Integer32
		
		MAX-ACCESS read-only
		STATUS current
		DESCRIPTION
		"upsApm160snmp_47_ModuleoutputCurrentC stored as 0.01A."
		::= { upsApm160snmpEntry 47 }
upsApm160snmp_48_ModuleoutputFrequency OBJECT-TYPE
		SYNTAX Integer32
		
		MAX-ACCESS read-only
		STATUS current
		DESCRIPTION
		"upsApm160snmp_48_ModuleoutputFrequency stored as 0.01Hz."
		::= { upsApm160snmpEntry 48 }
upsApm160snmp_49_ModuleoutputPowerFactorA OBJECT-TYPE
		SYNTAX Integer32
		
		MAX-ACCESS read-only
		STATUS current
		DESCRIPTION
		"upsApm160snmp_49_ModuleoutputPowerFactorA stored as 0.01."
		::= { upsApm160snmpEntry 49 }
upsApm160snmp_50_ModuleoutputPowerFactorB OBJECT-TYPE
		SYNTAX Integer32
		
		MAX-ACCESS read-only
		STATUS current
		DESCRIPTION
		"upsApm160snmp_50_ModuleoutputPowerFactorB stored as 0.01."
		::= { upsApm160snmpEntry 50 }
upsApm160snmp_51_ModuleoutputPowerFactorC OBJECT-TYPE
		SYNTAX Integer32
		
		MAX-ACCESS read-only
		STATUS current
		DESCRIPTION
		"upsApm160snmp_51_ModuleoutputPowerFactorC stored as 0.01."
		::= { upsApm160snmpEntry 51 }
upsApm160snmp_52_ModuleoutputAcitvePowerA OBJECT-TYPE
		SYNTAX Integer32
		
		MAX-ACCESS read-only
		STATUS current
		DESCRIPTION
		"upsApm160snmp_52_ModuleoutputAcitvePowerA stored as 0.01kW."
		::= { upsApm160snmpEntry 52 }
upsApm160snmp_53_ModuleoutputAcitvePowerB OBJECT-TYPE
		SYNTAX Integer32
		
		MAX-ACCESS read-only
		STATUS current
		DESCRIPTION
		"upsApm160snmp_53_ModuleoutputAcitvePowerB stored as 0.01kW."
		::= { upsApm160snmpEntry 53 }
upsApm160snmp_54_ModuleoutputAcitvePowerC OBJECT-TYPE
		SYNTAX Integer32
		
		MAX-ACCESS read-only
		STATUS current
		DESCRIPTION
		"upsApm160snmp_54_ModuleoutputAcitvePowerC stored as 0.01kW."
		::= { upsApm160snmpEntry 54 }
upsApm160snmp_55_ModuleoutputReactivePowerA OBJECT-TYPE
		SYNTAX Integer32
		
		MAX-ACCESS read-only
		STATUS current
		DESCRIPTION
		"upsApm160snmp_55_ModuleoutputReactivePowerA stored as 0.01kVar."
		::= { upsApm160snmpEntry 55 }
upsApm160snmp_56_ModuleoutputReactivePowerB OBJECT-TYPE
		SYNTAX Integer32
		
		MAX-ACCESS read-only
		STATUS current
		DESCRIPTION
		"upsApm160snmp_56_ModuleoutputReactivePowerB stored as 0.01kVar."
		::= { upsApm160snmpEntry 56 }
upsApm160snmp_57_ModuleoutputReactivePowerC OBJECT-TYPE
		SYNTAX Integer32
		
		MAX-ACCESS read-only
		STATUS current
		DESCRIPTION
		"upsApm160snmp_57_ModuleoutputReactivePowerC stored as 0.01kVar."
		::= { upsApm160snmpEntry 57 }
upsApm160snmp_58_ModuleoutputAppPowerA OBJECT-TYPE
		SYNTAX Integer32
		
		MAX-ACCESS read-only
		STATUS current
		DESCRIPTION
		"upsApm160snmp_58_ModuleoutputAppPowerA stored as 0.01kVA."
		::= { upsApm160snmpEntry 58 }
upsApm160snmp_59_ModuleoutputAppPowerB OBJECT-TYPE
		SYNTAX Integer32
		
		MAX-ACCESS read-only
		STATUS current
		DESCRIPTION
		"upsApm160snmp_59_ModuleoutputAppPowerB stored as 0.01kVA."
		::= { upsApm160snmpEntry 59 }
upsApm160snmp_60_ModuleoutputAppPowerC OBJECT-TYPE
		SYNTAX Integer32
		
		MAX-ACCESS read-only
		STATUS current
		DESCRIPTION
		"upsApm160snmp_60_ModuleoutputAppPowerC stored as 0.01kVA."
		::= { upsApm160snmpEntry 60 }
upsApm160snmp_61_ModuleoutputLoadA OBJECT-TYPE
		SYNTAX Integer32
		
		MAX-ACCESS read-only
		STATUS current
		DESCRIPTION
		"upsApm160snmp_61_ModuleoutputLoadA stored as 0.01%."
		::= { upsApm160snmpEntry 61 }
upsApm160snmp_62_ModuleoutputLoadB OBJECT-TYPE
		SYNTAX Integer32
		
		MAX-ACCESS read-only
		STATUS current
		DESCRIPTION
		"upsApm160snmp_62_ModuleoutputLoadB stored as 0.01%."
		::= { upsApm160snmpEntry 62 }
upsApm160snmp_63_ModuleoutputLoadC OBJECT-TYPE
		SYNTAX Integer32
		
		MAX-ACCESS read-only
		STATUS current
		DESCRIPTION
		"upsApm160snmp_63_ModuleoutputLoadC stored as 0.01%."
		::= { upsApm160snmpEntry 63 }
upsApm160snmp_64_ModuleoutputCrestFactorA OBJECT-TYPE
		SYNTAX Integer32
		
		MAX-ACCESS read-only
		STATUS current
		DESCRIPTION
		"upsApm160snmp_64_ModuleoutputCrestFactorA stored as 0.01."
		::= { upsApm160snmpEntry 64 }
upsApm160snmp_65_ModuleoutputCrestFactorB OBJECT-TYPE
		SYNTAX Integer32
		
		MAX-ACCESS read-only
		STATUS current
		DESCRIPTION
		"upsApm160snmp_65_ModuleoutputCrestFactorB stored as 0.01."
		::= { upsApm160snmpEntry 65 }
upsApm160snmp_66_ModuleoutputCrestFactorC OBJECT-TYPE
		SYNTAX Integer32
		
		MAX-ACCESS read-only
		STATUS current
		DESCRIPTION
		"upsApm160snmp_66_ModuleoutputCrestFactorC stored as 0.01."
		::= { upsApm160snmpEntry 66 }
upsApm160snmp_67_ModulebypassVoltageA OBJECT-TYPE
		SYNTAX Integer32
		
		MAX-ACCESS read-only
		STATUS current
		DESCRIPTION
		"upsApm160snmp_67_ModulebypassVoltageA stored as 0.01V."
		::= { upsApm160snmpEntry 67 }
upsApm160snmp_68_ModulebypassVoltageB OBJECT-TYPE
		SYNTAX Integer32
		
		MAX-ACCESS read-only
		STATUS current
		DESCRIPTION
		"upsApm160snmp_68_ModulebypassVoltageB stored as 0.01V."
		::= { upsApm160snmpEntry 68 }
upsApm160snmp_69_ModulebypassVoltageC OBJECT-TYPE
		SYNTAX Integer32
		
		MAX-ACCESS read-only
		STATUS current
		DESCRIPTION
		"upsApm160snmp_69_ModulebypassVoltageC stored as 0.01V."
		::= { upsApm160snmpEntry 69 }
upsApm160snmp_70_ModulebypassLineVoltageAB OBJECT-TYPE
		SYNTAX Integer32
		
		MAX-ACCESS read-only
		STATUS current
		DESCRIPTION
		"upsApm160snmp_70_ModulebypassLineVoltageAB stored as 0.01V."
		::= { upsApm160snmpEntry 70 }
upsApm160snmp_71_ModulebypassLineVoltageBC OBJECT-TYPE
		SYNTAX Integer32
		
		MAX-ACCESS read-only
		STATUS current
		DESCRIPTION
		"upsApm160snmp_71_ModulebypassLineVoltageBC stored as 0.01V."
		::= { upsApm160snmpEntry 71 }
upsApm160snmp_72_ModulebypassLineVoltageCA OBJECT-TYPE
		SYNTAX Integer32
		
		MAX-ACCESS read-only
		STATUS current
		DESCRIPTION
		"upsApm160snmp_72_ModulebypassLineVoltageCA stored as 0.01V."
		::= { upsApm160snmpEntry 72 }
upsApm160snmp_73_ModulebypassFrequency OBJECT-TYPE
		SYNTAX Integer32
		
		MAX-ACCESS read-only
		STATUS current
		DESCRIPTION
		"upsApm160snmp_73_ModulebypassFrequency stored as 0.01Hz."
		::= { upsApm160snmpEntry 73 }
upsApm160snmp_74_ModulebatteryRemainsTime OBJECT-TYPE
		SYNTAX Integer32
		
		MAX-ACCESS read-only
		STATUS current
		DESCRIPTION
		"upsApm160snmp_74_ModulebatteryRemainsTime stored as 0.01min."
		::= { upsApm160snmpEntry 74 }
upsApm160snmp_75_ModulebatteryPositiveVoltage OBJECT-TYPE
		SYNTAX Integer32
		
		MAX-ACCESS read-only
		STATUS current
		DESCRIPTION
		"upsApm160snmp_75_ModulebatteryPositiveVoltage stored as 0.01V."
		::= { upsApm160snmpEntry 75 }
upsApm160snmp_76_ModulebatteryPositiveCurrent OBJECT-TYPE
		SYNTAX Integer32
		
		MAX-ACCESS read-only
		STATUS current
		DESCRIPTION
		"upsApm160snmp_76_ModulebatteryPositiveCurrent stored as 0.01A."
		::= { upsApm160snmpEntry 76 }
upsApm160snmp_77_ModulebatteryNegativeVoltage OBJECT-TYPE
		SYNTAX Integer32
		
		MAX-ACCESS read-only
		STATUS current
		DESCRIPTION
		"upsApm160snmp_77_ModulebatteryNegativeVoltage stored as 0.01V."
		::= { upsApm160snmpEntry 77 }
upsApm160snmp_78_ModulebatteryNegativeCurrent OBJECT-TYPE
		SYNTAX Integer32
		
		MAX-ACCESS read-only
		STATUS current
		DESCRIPTION
		"upsApm160snmp_78_ModulebatteryNegativeCurrent stored as 0.01A."
		::= { upsApm160snmpEntry 78 }
upsApm160snmp_79_ModulebatteryAgingRate OBJECT-TYPE
		SYNTAX Integer32
		
		MAX-ACCESS read-only
		STATUS current
		DESCRIPTION
		"upsApm160snmp_79_ModulebatteryAgingRate stored as 0.01."
		::= { upsApm160snmpEntry 79 }
upsApm160snmp_80_ModulebatteryTemperature OBJECT-TYPE
		SYNTAX Integer32
		
		MAX-ACCESS read-only
		STATUS current
		DESCRIPTION
		"upsApm160snmp_80_ModulebatteryTemperature stored as 0.01℃."
		::= { upsApm160snmpEntry 80 }
upsApm160snmp_81_Module1inputPhaseVoltageA OBJECT-TYPE
		SYNTAX Integer32
		
		MAX-ACCESS read-only
		STATUS current
		DESCRIPTION
		"upsApm160snmp_81_Module1inputPhaseVoltageA stored as 0.01V."
		::= { upsApm160snmpEntry 81 }
upsApm160snmp_82_Module1inputPhaseVoltageB OBJECT-TYPE
		SYNTAX Integer32
		
		MAX-ACCESS read-only
		STATUS current
		DESCRIPTION
		"upsApm160snmp_82_Module1inputPhaseVoltageB stored as 0.01V."
		::= { upsApm160snmpEntry 82 }
upsApm160snmp_83_Module1inputPhaseVoltageC OBJECT-TYPE
		SYNTAX Integer32
		
		MAX-ACCESS read-only
		STATUS current
		DESCRIPTION
		"upsApm160snmp_83_Module1inputPhaseVoltageC stored as 0.01V."
		::= { upsApm160snmpEntry 83 }
upsApm160snmp_84_Module1inputLineVoltageA OBJECT-TYPE
		SYNTAX Integer32
		
		MAX-ACCESS read-only
		STATUS current
		DESCRIPTION
		"upsApm160snmp_84_Module1inputLineVoltageA stored as 0.01V."
		::= { upsApm160snmpEntry 84 }
upsApm160snmp_85_Module1inputLineVoltageB OBJECT-TYPE
		SYNTAX Integer32
		
		MAX-ACCESS read-only
		STATUS current
		DESCRIPTION
		"upsApm160snmp_85_Module1inputLineVoltageB stored as 0.01V."
		::= { upsApm160snmpEntry 85 }
upsApm160snmp_86_Module1inputLineVoltageC OBJECT-TYPE
		SYNTAX Integer32
		
		MAX-ACCESS read-only
		STATUS current
		DESCRIPTION
		"upsApm160snmp_86_Module1inputLineVoltageC stored as 0.01V."
		::= { upsApm160snmpEntry 86 }
upsApm160snmp_87_Module1inputCurrentA OBJECT-TYPE
		SYNTAX Integer32
		
		MAX-ACCESS read-only
		STATUS current
		DESCRIPTION
		"upsApm160snmp_87_Module1inputCurrentA stored as 0.01A."
		::= { upsApm160snmpEntry 87 }
upsApm160snmp_88_Module1inputCurrentB OBJECT-TYPE
		SYNTAX Integer32
		
		MAX-ACCESS read-only
		STATUS current
		DESCRIPTION
		"upsApm160snmp_88_Module1inputCurrentB stored as 0.01A."
		::= { upsApm160snmpEntry 88 }
upsApm160snmp_89_Module1inputCurrentC OBJECT-TYPE
		SYNTAX Integer32
		
		MAX-ACCESS read-only
		STATUS current
		DESCRIPTION
		"upsApm160snmp_89_Module1inputCurrentC stored as 0.01A."
		::= { upsApm160snmpEntry 89 }
upsApm160snmp_90_Module1inputFrequency OBJECT-TYPE
		SYNTAX Integer32
		
		MAX-ACCESS read-only
		STATUS current
		DESCRIPTION
		"upsApm160snmp_90_Module1inputFrequency stored as 0.01Hz."
		::= { upsApm160snmpEntry 90 }
upsApm160snmp_91_Module1inputPowerFactorA OBJECT-TYPE
		SYNTAX Integer32
		
		MAX-ACCESS read-only
		STATUS current
		DESCRIPTION
		"upsApm160snmp_91_Module1inputPowerFactorA stored as 0.01."
		::= { upsApm160snmpEntry 91 }
upsApm160snmp_92_Module1inputPowerFactorB OBJECT-TYPE
		SYNTAX Integer32
		
		MAX-ACCESS read-only
		STATUS current
		DESCRIPTION
		"upsApm160snmp_92_Module1inputPowerFactorB stored as 0.01."
		::= { upsApm160snmpEntry 92 }
upsApm160snmp_93_Module1inputPowerFactorC OBJECT-TYPE
		SYNTAX Integer32
		
		MAX-ACCESS read-only
		STATUS current
		DESCRIPTION
		"upsApm160snmp_93_Module1inputPowerFactorC stored as 0.01."
		::= { upsApm160snmpEntry 93 }
upsApm160snmp_94_Module1batteryVoltage OBJECT-TYPE
		SYNTAX Integer32
		
		MAX-ACCESS read-only
		STATUS current
		DESCRIPTION
		"upsApm160snmp_94_Module1batteryVoltage stored as 0.01V."
		::= { upsApm160snmpEntry 94 }
upsApm160snmp_95_Module1inputActivePowerA OBJECT-TYPE
		SYNTAX Integer32
		
		MAX-ACCESS read-only
		STATUS current
		DESCRIPTION
		"upsApm160snmp_95_Module1inputActivePowerA stored as 0.01kW."
		::= { upsApm160snmpEntry 95 }
upsApm160snmp_96_Module1inputActivePowerB OBJECT-TYPE
		SYNTAX Integer32
		
		MAX-ACCESS read-only
		STATUS current
		DESCRIPTION
		"upsApm160snmp_96_Module1inputActivePowerB stored as 0.01kW."
		::= { upsApm160snmpEntry 96 }
upsApm160snmp_97_Module1inputActivePowerC OBJECT-TYPE
		SYNTAX Integer32
		
		MAX-ACCESS read-only
		STATUS current
		DESCRIPTION
		"upsApm160snmp_97_Module1inputActivePowerC stored as 0.01kW."
		::= { upsApm160snmpEntry 97 }
upsApm160snmp_98_Module1inputAppPowerA OBJECT-TYPE
		SYNTAX Integer32
		
		MAX-ACCESS read-only
		STATUS current
		DESCRIPTION
		"upsApm160snmp_98_Module1inputAppPowerA stored as 0.01kVA."
		::= { upsApm160snmpEntry 98 }
upsApm160snmp_99_Module1inputAppPowerB OBJECT-TYPE
		SYNTAX Integer32
		
		MAX-ACCESS read-only
		STATUS current
		DESCRIPTION
		"upsApm160snmp_99_Module1inputAppPowerB stored as 0.01kVA."
		::= { upsApm160snmpEntry 99 }
upsApm160snmp_100_Module1inputAppPowerC OBJECT-TYPE
		SYNTAX Integer32
		
		MAX-ACCESS read-only
		STATUS current
		DESCRIPTION
		"upsApm160snmp_100_Module1inputAppPowerC stored as 0.01kVA."
		::= { upsApm160snmpEntry 100 }
upsApm160snmp_101_Module1inputEnergyA OBJECT-TYPE
		SYNTAX Integer32
		
		MAX-ACCESS read-only
		STATUS current
		DESCRIPTION
		"upsApm160snmp_101_Module1inputEnergyA stored as 0.01kWh."
		::= { upsApm160snmpEntry 101 }
upsApm160snmp_102_Module1inputEnergyB OBJECT-TYPE
		SYNTAX Integer32
		
		MAX-ACCESS read-only
		STATUS current
		DESCRIPTION
		"upsApm160snmp_102_Module1inputEnergyB stored as 0.01kWh."
		::= { upsApm160snmpEntry 102 }
upsApm160snmp_103_Module1inputEnergyC OBJECT-TYPE
		SYNTAX Integer32
		
		MAX-ACCESS read-only
		STATUS current
		DESCRIPTION
		"upsApm160snmp_103_Module1inputEnergyC stored as 0.01kWh."
		::= { upsApm160snmpEntry 103 }
upsApm160snmp_104_Module1outputVoltageA OBJECT-TYPE
		SYNTAX Integer32
		
		MAX-ACCESS read-only
		STATUS current
		DESCRIPTION
		"upsApm160snmp_104_Module1outputVoltageA stored as 0.01V."
		::= { upsApm160snmpEntry 104 }
upsApm160snmp_105_Module1outputVoltageB OBJECT-TYPE
		SYNTAX Integer32
		
		MAX-ACCESS read-only
		STATUS current
		DESCRIPTION
		"upsApm160snmp_105_Module1outputVoltageB stored as 0.01V."
		::= { upsApm160snmpEntry 105 }
upsApm160snmp_106_Module1outputVoltageC OBJECT-TYPE
		SYNTAX Integer32
		
		MAX-ACCESS read-only
		STATUS current
		DESCRIPTION
		"upsApm160snmp_106_Module1outputVoltageC stored as 0.01V."
		::= { upsApm160snmpEntry 106 }
upsApm160snmp_107_Module1outputLineVoltageAB OBJECT-TYPE
		SYNTAX Integer32
		
		MAX-ACCESS read-only
		STATUS current
		DESCRIPTION
		"upsApm160snmp_107_Module1outputLineVoltageAB stored as 0.01V."
		::= { upsApm160snmpEntry 107 }
upsApm160snmp_108_Module1outputLineVoltageBC OBJECT-TYPE
		SYNTAX Integer32
		
		MAX-ACCESS read-only
		STATUS current
		DESCRIPTION
		"upsApm160snmp_108_Module1outputLineVoltageBC stored as 0.01V."
		::= { upsApm160snmpEntry 108 }
upsApm160snmp_109_Module1outputLineVoltageCA OBJECT-TYPE
		SYNTAX Integer32
		
		MAX-ACCESS read-only
		STATUS current
		DESCRIPTION
		"upsApm160snmp_109_Module1outputLineVoltageCA stored as 0.01V."
		::= { upsApm160snmpEntry 109 }
upsApm160snmp_110_Module1outputCurrentA OBJECT-TYPE
		SYNTAX Integer32
		
		MAX-ACCESS read-only
		STATUS current
		DESCRIPTION
		"upsApm160snmp_110_Module1outputCurrentA stored as 0.01A."
		::= { upsApm160snmpEntry 110 }
upsApm160snmp_111_Module1outputCurrentB OBJECT-TYPE
		SYNTAX Integer32
		
		MAX-ACCESS read-only
		STATUS current
		DESCRIPTION
		"upsApm160snmp_111_Module1outputCurrentB stored as 0.01A."
		::= { upsApm160snmpEntry 111 }
upsApm160snmp_112_Module1outputCurrentC OBJECT-TYPE
		SYNTAX Integer32
		
		MAX-ACCESS read-only
		STATUS current
		DESCRIPTION
		"upsApm160snmp_112_Module1outputCurrentC stored as 0.01A."
		::= { upsApm160snmpEntry 112 }
upsApm160snmp_113_Module1outputFrequency OBJECT-TYPE
		SYNTAX Integer32
		
		MAX-ACCESS read-only
		STATUS current
		DESCRIPTION
		"upsApm160snmp_113_Module1outputFrequency stored as 0.01Hz."
		::= { upsApm160snmpEntry 113 }
upsApm160snmp_114_Module1outputPowerFactorA OBJECT-TYPE
		SYNTAX Integer32
		
		MAX-ACCESS read-only
		STATUS current
		DESCRIPTION
		"upsApm160snmp_114_Module1outputPowerFactorA stored as 0.01."
		::= { upsApm160snmpEntry 114 }
upsApm160snmp_115_Module1outputPowerFactorB OBJECT-TYPE
		SYNTAX Integer32
		
		MAX-ACCESS read-only
		STATUS current
		DESCRIPTION
		"upsApm160snmp_115_Module1outputPowerFactorB stored as 0.01."
		::= { upsApm160snmpEntry 115 }
upsApm160snmp_116_Module1outputPowerFactorC OBJECT-TYPE
		SYNTAX Integer32
		
		MAX-ACCESS read-only
		STATUS current
		DESCRIPTION
		"upsApm160snmp_116_Module1outputPowerFactorC stored as 0.01."
		::= { upsApm160snmpEntry 116 }
upsApm160snmp_117_Module1outputAcitvePowerA OBJECT-TYPE
		SYNTAX Integer32
		
		MAX-ACCESS read-only
		STATUS current
		DESCRIPTION
		"upsApm160snmp_117_Module1outputAcitvePowerA stored as 0.01kW."
		::= { upsApm160snmpEntry 117 }
upsApm160snmp_118_Module1outputAcitvePowerB OBJECT-TYPE
		SYNTAX Integer32
		
		MAX-ACCESS read-only
		STATUS current
		DESCRIPTION
		"upsApm160snmp_118_Module1outputAcitvePowerB stored as 0.01kW."
		::= { upsApm160snmpEntry 118 }
upsApm160snmp_119_Module1outputAcitvePowerC OBJECT-TYPE
		SYNTAX Integer32
		
		MAX-ACCESS read-only
		STATUS current
		DESCRIPTION
		"upsApm160snmp_119_Module1outputAcitvePowerC stored as 0.01kW."
		::= { upsApm160snmpEntry 119 }
upsApm160snmp_120_Module1outputReactivePowerA OBJECT-TYPE
		SYNTAX Integer32
		
		MAX-ACCESS read-only
		STATUS current
		DESCRIPTION
		"upsApm160snmp_120_Module1outputReactivePowerA stored as 0.01kVar."
		::= { upsApm160snmpEntry 120 }
upsApm160snmp_121_Module1outputReactivePowerB OBJECT-TYPE
		SYNTAX Integer32
		
		MAX-ACCESS read-only
		STATUS current
		DESCRIPTION
		"upsApm160snmp_121_Module1outputReactivePowerB stored as 0.01kVar."
		::= { upsApm160snmpEntry 121 }
upsApm160snmp_122_Module1outputReactivePowerC OBJECT-TYPE
		SYNTAX Integer32
		
		MAX-ACCESS read-only
		STATUS current
		DESCRIPTION
		"upsApm160snmp_122_Module1outputReactivePowerC stored as 0.01kVar."
		::= { upsApm160snmpEntry 122 }
upsApm160snmp_123_Module1outputAppPowerA OBJECT-TYPE
		SYNTAX Integer32
		
		MAX-ACCESS read-only
		STATUS current
		DESCRIPTION
		"upsApm160snmp_123_Module1outputAppPowerA stored as 0.01kVA."
		::= { upsApm160snmpEntry 123 }
upsApm160snmp_124_Module1outputAppPowerB OBJECT-TYPE
		SYNTAX Integer32
		
		MAX-ACCESS read-only
		STATUS current
		DESCRIPTION
		"upsApm160snmp_124_Module1outputAppPowerB stored as 0.01kVA."
		::= { upsApm160snmpEntry 124 }
upsApm160snmp_125_Module1outputAppPowerC OBJECT-TYPE
		SYNTAX Integer32
		
		MAX-ACCESS read-only
		STATUS current
		DESCRIPTION
		"upsApm160snmp_125_Module1outputAppPowerC stored as 0.01kVA."
		::= { upsApm160snmpEntry 125 }
upsApm160snmp_126_Module1outputLoadA OBJECT-TYPE
		SYNTAX Integer32
		
		MAX-ACCESS read-only
		STATUS current
		DESCRIPTION
		"upsApm160snmp_126_Module1outputLoadA stored as 0.01%."
		::= { upsApm160snmpEntry 126 }
upsApm160snmp_127_Module1outputLoadB OBJECT-TYPE
		SYNTAX Integer32
		
		MAX-ACCESS read-only
		STATUS current
		DESCRIPTION
		"upsApm160snmp_127_Module1outputLoadB stored as 0.01%."
		::= { upsApm160snmpEntry 127 }
upsApm160snmp_128_Module1outputLoadC OBJECT-TYPE
		SYNTAX Integer32
		
		MAX-ACCESS read-only
		STATUS current
		DESCRIPTION
		"upsApm160snmp_128_Module1outputLoadC stored as 0.01%."
		::= { upsApm160snmpEntry 128 }
upsApm160snmp_129_Module1outputCrestFactorA OBJECT-TYPE
		SYNTAX Integer32
		
		MAX-ACCESS read-only
		STATUS current
		DESCRIPTION
		"upsApm160snmp_129_Module1outputCrestFactorA stored as 0.01."
		::= { upsApm160snmpEntry 129 }
upsApm160snmp_130_Module1outputCrestFactorB OBJECT-TYPE
		SYNTAX Integer32
		
		MAX-ACCESS read-only
		STATUS current
		DESCRIPTION
		"upsApm160snmp_130_Module1outputCrestFactorB stored as 0.01."
		::= { upsApm160snmpEntry 130 }
upsApm160snmp_131_Module1outputCrestFactorC OBJECT-TYPE
		SYNTAX Integer32
		
		MAX-ACCESS read-only
		STATUS current
		DESCRIPTION
		"upsApm160snmp_131_Module1outputCrestFactorC stored as 0.01."
		::= { upsApm160snmpEntry 131 }
upsApm160snmp_132_Module1bypassVoltageA OBJECT-TYPE
		SYNTAX Integer32
		
		MAX-ACCESS read-only
		STATUS current
		DESCRIPTION
		"upsApm160snmp_132_Module1bypassVoltageA stored as 0.01V."
		::= { upsApm160snmpEntry 132 }
upsApm160snmp_133_Module1bypassVoltageB OBJECT-TYPE
		SYNTAX Integer32
		
		MAX-ACCESS read-only
		STATUS current
		DESCRIPTION
		"upsApm160snmp_133_Module1bypassVoltageB stored as 0.01V."
		::= { upsApm160snmpEntry 133 }
upsApm160snmp_134_Module1bypassVoltageC OBJECT-TYPE
		SYNTAX Integer32
		
		MAX-ACCESS read-only
		STATUS current
		DESCRIPTION
		"upsApm160snmp_134_Module1bypassVoltageC stored as 0.01V."
		::= { upsApm160snmpEntry 134 }
upsApm160snmp_135_Module1bypassLineVoltageAB OBJECT-TYPE
		SYNTAX Integer32
		
		MAX-ACCESS read-only
		STATUS current
		DESCRIPTION
		"upsApm160snmp_135_Module1bypassLineVoltageAB stored as 0.01V."
		::= { upsApm160snmpEntry 135 }
upsApm160snmp_136_Module1bypassLineVoltageBC OBJECT-TYPE
		SYNTAX Integer32
		
		MAX-ACCESS read-only
		STATUS current
		DESCRIPTION
		"upsApm160snmp_136_Module1bypassLineVoltageBC stored as 0.01V."
		::= { upsApm160snmpEntry 136 }
upsApm160snmp_137_Module1bypassLineVoltageCA OBJECT-TYPE
		SYNTAX Integer32
		
		MAX-ACCESS read-only
		STATUS current
		DESCRIPTION
		"upsApm160snmp_137_Module1bypassLineVoltageCA stored as 0.01V."
		::= { upsApm160snmpEntry 137 }
upsApm160snmp_138_Module1bypassFrequency OBJECT-TYPE
		SYNTAX Integer32
		
		MAX-ACCESS read-only
		STATUS current
		DESCRIPTION
		"upsApm160snmp_138_Module1bypassFrequency stored as 0.01Hz."
		::= { upsApm160snmpEntry 138 }
upsApm160snmp_139_Module1batteryRemainsTime OBJECT-TYPE
		SYNTAX Integer32
		
		MAX-ACCESS read-only
		STATUS current
		DESCRIPTION
		"upsApm160snmp_139_Module1batteryRemainsTime stored as 0.01min."
		::= { upsApm160snmpEntry 139 }
upsApm160snmp_140_Module1batteryPositiveVoltage OBJECT-TYPE
		SYNTAX Integer32
		
		MAX-ACCESS read-only
		STATUS current
		DESCRIPTION
		"upsApm160snmp_140_Module1batteryPositiveVoltage stored as 0.01V."
		::= { upsApm160snmpEntry 140 }
upsApm160snmp_141_Module1batteryPositiveCurrent OBJECT-TYPE
		SYNTAX Integer32
		
		MAX-ACCESS read-only
		STATUS current
		DESCRIPTION
		"upsApm160snmp_141_Module1batteryPositiveCurrent stored as 0.01A."
		::= { upsApm160snmpEntry 141 }
upsApm160snmp_142_Module1batteryNegativeVoltage OBJECT-TYPE
		SYNTAX Integer32
		
		MAX-ACCESS read-only
		STATUS current
		DESCRIPTION
		"upsApm160snmp_142_Module1batteryNegativeVoltage stored as 0.01V."
		::= { upsApm160snmpEntry 142 }
upsApm160snmp_143_Module1batteryNegativeCurrent OBJECT-TYPE
		SYNTAX Integer32
		
		MAX-ACCESS read-only
		STATUS current
		DESCRIPTION
		"upsApm160snmp_143_Module1batteryNegativeCurrent stored as 0.01A."
		::= { upsApm160snmpEntry 143 }
upsApm160snmp_144_Module1batteryAgingRate OBJECT-TYPE
		SYNTAX Integer32
		
		MAX-ACCESS read-only
		STATUS current
		DESCRIPTION
		"upsApm160snmp_144_Module1batteryAgingRate stored as 0.01."
		::= { upsApm160snmpEntry 144 }
upsApm160snmp_145_Module1batteryTemperature OBJECT-TYPE
		SYNTAX Integer32
		
		MAX-ACCESS read-only
		STATUS current
		DESCRIPTION
		"upsApm160snmp_145_Module1batteryTemperature stored as 0.01℃."
		::= { upsApm160snmpEntry 145 }
upsApm160snmp_146_Module2inputPhaseVoltageA OBJECT-TYPE
		SYNTAX Integer32
		
		MAX-ACCESS read-only
		STATUS current
		DESCRIPTION
		"upsApm160snmp_146_Module2inputPhaseVoltageA stored as 0.01V."
		::= { upsApm160snmpEntry 146 }
upsApm160snmp_147_Module2inputPhaseVoltageB OBJECT-TYPE
		SYNTAX Integer32
		
		MAX-ACCESS read-only
		STATUS current
		DESCRIPTION
		"upsApm160snmp_147_Module2inputPhaseVoltageB stored as 0.01V."
		::= { upsApm160snmpEntry 147 }
upsApm160snmp_148_Module2inputPhaseVoltageC OBJECT-TYPE
		SYNTAX Integer32
		
		MAX-ACCESS read-only
		STATUS current
		DESCRIPTION
		"upsApm160snmp_148_Module2inputPhaseVoltageC stored as 0.01V."
		::= { upsApm160snmpEntry 148 }
upsApm160snmp_149_Module2inputLineVoltageA OBJECT-TYPE
		SYNTAX Integer32
		
		MAX-ACCESS read-only
		STATUS current
		DESCRIPTION
		"upsApm160snmp_149_Module2inputLineVoltageA stored as 0.01V."
		::= { upsApm160snmpEntry 149 }
upsApm160snmp_150_Module2inputLineVoltageB OBJECT-TYPE
		SYNTAX Integer32
		
		MAX-ACCESS read-only
		STATUS current
		DESCRIPTION
		"upsApm160snmp_150_Module2inputLineVoltageB stored as 0.01V."
		::= { upsApm160snmpEntry 150 }
upsApm160snmp_151_Module2inputLineVoltageC OBJECT-TYPE
		SYNTAX Integer32
		
		MAX-ACCESS read-only
		STATUS current
		DESCRIPTION
		"upsApm160snmp_151_Module2inputLineVoltageC stored as 0.01V."
		::= { upsApm160snmpEntry 151 }
upsApm160snmp_152_Module2inputCurrentA OBJECT-TYPE
		SYNTAX Integer32
		
		MAX-ACCESS read-only
		STATUS current
		DESCRIPTION
		"upsApm160snmp_152_Module2inputCurrentA stored as 0.01A."
		::= { upsApm160snmpEntry 152 }
upsApm160snmp_153_Module2inputCurrentB OBJECT-TYPE
		SYNTAX Integer32
		
		MAX-ACCESS read-only
		STATUS current
		DESCRIPTION
		"upsApm160snmp_153_Module2inputCurrentB stored as 0.01A."
		::= { upsApm160snmpEntry 153 }
upsApm160snmp_154_Module2inputCurrentC OBJECT-TYPE
		SYNTAX Integer32
		
		MAX-ACCESS read-only
		STATUS current
		DESCRIPTION
		"upsApm160snmp_154_Module2inputCurrentC stored as 0.01A."
		::= { upsApm160snmpEntry 154 }
upsApm160snmp_155_Module2inputFrequency OBJECT-TYPE
		SYNTAX Integer32
		
		MAX-ACCESS read-only
		STATUS current
		DESCRIPTION
		"upsApm160snmp_155_Module2inputFrequency stored as 0.01Hz."
		::= { upsApm160snmpEntry 155 }
upsApm160snmp_156_Module2inputPowerFactorA OBJECT-TYPE
		SYNTAX Integer32
		
		MAX-ACCESS read-only
		STATUS current
		DESCRIPTION
		"upsApm160snmp_156_Module2inputPowerFactorA stored as 0.01."
		::= { upsApm160snmpEntry 156 }
upsApm160snmp_157_Module2inputPowerFactorB OBJECT-TYPE
		SYNTAX Integer32
		
		MAX-ACCESS read-only
		STATUS current
		DESCRIPTION
		"upsApm160snmp_157_Module2inputPowerFactorB stored as 0.01."
		::= { upsApm160snmpEntry 157 }
upsApm160snmp_158_Module2inputPowerFactorC OBJECT-TYPE
		SYNTAX Integer32
		
		MAX-ACCESS read-only
		STATUS current
		DESCRIPTION
		"upsApm160snmp_158_Module2inputPowerFactorC stored as 0.01."
		::= { upsApm160snmpEntry 158 }
upsApm160snmp_159_Module2batteryVoltage OBJECT-TYPE
		SYNTAX Integer32
		
		MAX-ACCESS read-only
		STATUS current
		DESCRIPTION
		"upsApm160snmp_159_Module2batteryVoltage stored as 0.01V."
		::= { upsApm160snmpEntry 159 }
upsApm160snmp_160_Module2inputActivePowerA OBJECT-TYPE
		SYNTAX Integer32
		
		MAX-ACCESS read-only
		STATUS current
		DESCRIPTION
		"upsApm160snmp_160_Module2inputActivePowerA stored as 0.01kW."
		::= { upsApm160snmpEntry 160 }
upsApm160snmp_161_Module2inputActivePowerB OBJECT-TYPE
		SYNTAX Integer32
		
		MAX-ACCESS read-only
		STATUS current
		DESCRIPTION
		"upsApm160snmp_161_Module2inputActivePowerB stored as 0.01kW."
		::= { upsApm160snmpEntry 161 }
upsApm160snmp_162_Module2inputActivePowerC OBJECT-TYPE
		SYNTAX Integer32
		
		MAX-ACCESS read-only
		STATUS current
		DESCRIPTION
		"upsApm160snmp_162_Module2inputActivePowerC stored as 0.01kW."
		::= { upsApm160snmpEntry 162 }
upsApm160snmp_163_Module2inputAppPowerA OBJECT-TYPE
		SYNTAX Integer32
		
		MAX-ACCESS read-only
		STATUS current
		DESCRIPTION
		"upsApm160snmp_163_Module2inputAppPowerA stored as 0.01kVA."
		::= { upsApm160snmpEntry 163 }
upsApm160snmp_164_Module2inputAppPowerB OBJECT-TYPE
		SYNTAX Integer32
		
		MAX-ACCESS read-only
		STATUS current
		DESCRIPTION
		"upsApm160snmp_164_Module2inputAppPowerB stored as 0.01kVA."
		::= { upsApm160snmpEntry 164 }
upsApm160snmp_165_Module2inputAppPowerC OBJECT-TYPE
		SYNTAX Integer32
		
		MAX-ACCESS read-only
		STATUS current
		DESCRIPTION
		"upsApm160snmp_165_Module2inputAppPowerC stored as 0.01kVA."
		::= { upsApm160snmpEntry 165 }
upsApm160snmp_166_Module2inputEnergyA OBJECT-TYPE
		SYNTAX Integer32
		
		MAX-ACCESS read-only
		STATUS current
		DESCRIPTION
		"upsApm160snmp_166_Module2inputEnergyA stored as 0.01kWh."
		::= { upsApm160snmpEntry 166 }
upsApm160snmp_167_Module2inputEnergyB OBJECT-TYPE
		SYNTAX Integer32
		
		MAX-ACCESS read-only
		STATUS current
		DESCRIPTION
		"upsApm160snmp_167_Module2inputEnergyB stored as 0.01kWh."
		::= { upsApm160snmpEntry 167 }
upsApm160snmp_168_Module2inputEnergyC OBJECT-TYPE
		SYNTAX Integer32
		
		MAX-ACCESS read-only
		STATUS current
		DESCRIPTION
		"upsApm160snmp_168_Module2inputEnergyC stored as 0.01kWh."
		::= { upsApm160snmpEntry 168 }
upsApm160snmp_169_Module2outputVoltageA OBJECT-TYPE
		SYNTAX Integer32
		
		MAX-ACCESS read-only
		STATUS current
		DESCRIPTION
		"upsApm160snmp_169_Module2outputVoltageA stored as 0.01V."
		::= { upsApm160snmpEntry 169 }
upsApm160snmp_170_Module2outputVoltageB OBJECT-TYPE
		SYNTAX Integer32
		
		MAX-ACCESS read-only
		STATUS current
		DESCRIPTION
		"upsApm160snmp_170_Module2outputVoltageB stored as 0.01V."
		::= { upsApm160snmpEntry 170 }
upsApm160snmp_171_Module2outputVoltageC OBJECT-TYPE
		SYNTAX Integer32
		
		MAX-ACCESS read-only
		STATUS current
		DESCRIPTION
		"upsApm160snmp_171_Module2outputVoltageC stored as 0.01V."
		::= { upsApm160snmpEntry 171 }
upsApm160snmp_172_Module2outputLineVoltageAB OBJECT-TYPE
		SYNTAX Integer32
		
		MAX-ACCESS read-only
		STATUS current
		DESCRIPTION
		"upsApm160snmp_172_Module2outputLineVoltageAB stored as 0.01V."
		::= { upsApm160snmpEntry 172 }
upsApm160snmp_173_Module2outputLineVoltageBC OBJECT-TYPE
		SYNTAX Integer32
		
		MAX-ACCESS read-only
		STATUS current
		DESCRIPTION
		"upsApm160snmp_173_Module2outputLineVoltageBC stored as 0.01V."
		::= { upsApm160snmpEntry 173 }
upsApm160snmp_174_Module2outputLineVoltageCA OBJECT-TYPE
		SYNTAX Integer32
		
		MAX-ACCESS read-only
		STATUS current
		DESCRIPTION
		"upsApm160snmp_174_Module2outputLineVoltageCA stored as 0.01V."
		::= { upsApm160snmpEntry 174 }
upsApm160snmp_175_Module2outputCurrentA OBJECT-TYPE
		SYNTAX Integer32
		
		MAX-ACCESS read-only
		STATUS current
		DESCRIPTION
		"upsApm160snmp_175_Module2outputCurrentA stored as 0.01A."
		::= { upsApm160snmpEntry 175 }
upsApm160snmp_176_Module2outputCurrentB OBJECT-TYPE
		SYNTAX Integer32
		
		MAX-ACCESS read-only
		STATUS current
		DESCRIPTION
		"upsApm160snmp_176_Module2outputCurrentB stored as 0.01A."
		::= { upsApm160snmpEntry 176 }
upsApm160snmp_177_Module2outputCurrentC OBJECT-TYPE
		SYNTAX Integer32
		
		MAX-ACCESS read-only
		STATUS current
		DESCRIPTION
		"upsApm160snmp_177_Module2outputCurrentC stored as 0.01A."
		::= { upsApm160snmpEntry 177 }
upsApm160snmp_178_Module2outputFrequency OBJECT-TYPE
		SYNTAX Integer32
		
		MAX-ACCESS read-only
		STATUS current
		DESCRIPTION
		"upsApm160snmp_178_Module2outputFrequency stored as 0.01Hz."
		::= { upsApm160snmpEntry 178 }
upsApm160snmp_179_Module2outputPowerFactorA OBJECT-TYPE
		SYNTAX Integer32
		
		MAX-ACCESS read-only
		STATUS current
		DESCRIPTION
		"upsApm160snmp_179_Module2outputPowerFactorA stored as 0.01."
		::= { upsApm160snmpEntry 179 }
upsApm160snmp_180_Module2outputPowerFactorB OBJECT-TYPE
		SYNTAX Integer32
		
		MAX-ACCESS read-only
		STATUS current
		DESCRIPTION
		"upsApm160snmp_180_Module2outputPowerFactorB stored as 0.01."
		::= { upsApm160snmpEntry 180 }
upsApm160snmp_181_Module2outputPowerFactorC OBJECT-TYPE
		SYNTAX Integer32
		
		MAX-ACCESS read-only
		STATUS current
		DESCRIPTION
		"upsApm160snmp_181_Module2outputPowerFactorC stored as 0.01."
		::= { upsApm160snmpEntry 181 }
upsApm160snmp_182_Module2outputAcitvePowerA OBJECT-TYPE
		SYNTAX Integer32
		
		MAX-ACCESS read-only
		STATUS current
		DESCRIPTION
		"upsApm160snmp_182_Module2outputAcitvePowerA stored as 0.01kW."
		::= { upsApm160snmpEntry 182 }
upsApm160snmp_183_Module2outputAcitvePowerB OBJECT-TYPE
		SYNTAX Integer32
		
		MAX-ACCESS read-only
		STATUS current
		DESCRIPTION
		"upsApm160snmp_183_Module2outputAcitvePowerB stored as 0.01kW."
		::= { upsApm160snmpEntry 183 }
upsApm160snmp_184_Module2outputAcitvePowerC OBJECT-TYPE
		SYNTAX Integer32
		
		MAX-ACCESS read-only
		STATUS current
		DESCRIPTION
		"upsApm160snmp_184_Module2outputAcitvePowerC stored as 0.01kW."
		::= { upsApm160snmpEntry 184 }
upsApm160snmp_185_Module2outputReactivePowerA OBJECT-TYPE
		SYNTAX Integer32
		
		MAX-ACCESS read-only
		STATUS current
		DESCRIPTION
		"upsApm160snmp_185_Module2outputReactivePowerA stored as 0.01kVar."
		::= { upsApm160snmpEntry 185 }
upsApm160snmp_186_Module2outputReactivePowerB OBJECT-TYPE
		SYNTAX Integer32
		
		MAX-ACCESS read-only
		STATUS current
		DESCRIPTION
		"upsApm160snmp_186_Module2outputReactivePowerB stored as 0.01kVar."
		::= { upsApm160snmpEntry 186 }
upsApm160snmp_187_Module2outputReactivePowerC OBJECT-TYPE
		SYNTAX Integer32
		
		MAX-ACCESS read-only
		STATUS current
		DESCRIPTION
		"upsApm160snmp_187_Module2outputReactivePowerC stored as 0.01kVar."
		::= { upsApm160snmpEntry 187 }
upsApm160snmp_188_Module2outputAppPowerA OBJECT-TYPE
		SYNTAX Integer32
		
		MAX-ACCESS read-only
		STATUS current
		DESCRIPTION
		"upsApm160snmp_188_Module2outputAppPowerA stored as 0.01kVA."
		::= { upsApm160snmpEntry 188 }
upsApm160snmp_189_Module2outputAppPowerB OBJECT-TYPE
		SYNTAX Integer32
		
		MAX-ACCESS read-only
		STATUS current
		DESCRIPTION
		"upsApm160snmp_189_Module2outputAppPowerB stored as 0.01kVA."
		::= { upsApm160snmpEntry 189 }
upsApm160snmp_190_Module2outputAppPowerC OBJECT-TYPE
		SYNTAX Integer32
		
		MAX-ACCESS read-only
		STATUS current
		DESCRIPTION
		"upsApm160snmp_190_Module2outputAppPowerC stored as 0.01kVA."
		::= { upsApm160snmpEntry 190 }
upsApm160snmp_191_Module2outputLoadA OBJECT-TYPE
		SYNTAX Integer32
		
		MAX-ACCESS read-only
		STATUS current
		DESCRIPTION
		"upsApm160snmp_191_Module2outputLoadA stored as 0.01%."
		::= { upsApm160snmpEntry 191 }
upsApm160snmp_192_Module2outputLoadB OBJECT-TYPE
		SYNTAX Integer32
		
		MAX-ACCESS read-only
		STATUS current
		DESCRIPTION
		"upsApm160snmp_192_Module2outputLoadB stored as 0.01%."
		::= { upsApm160snmpEntry 192 }
upsApm160snmp_193_Module2outputLoadC OBJECT-TYPE
		SYNTAX Integer32
		
		MAX-ACCESS read-only
		STATUS current
		DESCRIPTION
		"upsApm160snmp_193_Module2outputLoadC stored as 0.01%."
		::= { upsApm160snmpEntry 193 }
upsApm160snmp_194_Module2outputCrestFactorA OBJECT-TYPE
		SYNTAX Integer32
		
		MAX-ACCESS read-only
		STATUS current
		DESCRIPTION
		"upsApm160snmp_194_Module2outputCrestFactorA stored as 0.01."
		::= { upsApm160snmpEntry 194 }
upsApm160snmp_195_Module2outputCrestFactorB OBJECT-TYPE
		SYNTAX Integer32
		
		MAX-ACCESS read-only
		STATUS current
		DESCRIPTION
		"upsApm160snmp_195_Module2outputCrestFactorB stored as 0.01."
		::= { upsApm160snmpEntry 195 }
upsApm160snmp_196_Module2outputCrestFactorC OBJECT-TYPE
		SYNTAX Integer32
		
		MAX-ACCESS read-only
		STATUS current
		DESCRIPTION
		"upsApm160snmp_196_Module2outputCrestFactorC stored as 0.01."
		::= { upsApm160snmpEntry 196 }
upsApm160snmp_197_Module2bypassVoltageA OBJECT-TYPE
		SYNTAX Integer32
		
		MAX-ACCESS read-only
		STATUS current
		DESCRIPTION
		"upsApm160snmp_197_Module2bypassVoltageA stored as 0.01V."
		::= { upsApm160snmpEntry 197 }
upsApm160snmp_198_Module2bypassVoltageB OBJECT-TYPE
		SYNTAX Integer32
		
		MAX-ACCESS read-only
		STATUS current
		DESCRIPTION
		"upsApm160snmp_198_Module2bypassVoltageB stored as 0.01V."
		::= { upsApm160snmpEntry 198 }
upsApm160snmp_199_Module2bypassVoltageC OBJECT-TYPE
		SYNTAX Integer32
		
		MAX-ACCESS read-only
		STATUS current
		DESCRIPTION
		"upsApm160snmp_199_Module2bypassVoltageC stored as 0.01V."
		::= { upsApm160snmpEntry 199 }
upsApm160snmp_200_Module2bypassLineVoltageAB OBJECT-TYPE
		SYNTAX Integer32
		
		MAX-ACCESS read-only
		STATUS current
		DESCRIPTION
		"upsApm160snmp_200_Module2bypassLineVoltageAB stored as 0.01V."
		::= { upsApm160snmpEntry 200 }
upsApm160snmp_201_Module2bypassLineVoltageBC OBJECT-TYPE
		SYNTAX Integer32
		
		MAX-ACCESS read-only
		STATUS current
		DESCRIPTION
		"upsApm160snmp_201_Module2bypassLineVoltageBC stored as 0.01V."
		::= { upsApm160snmpEntry 201 }
upsApm160snmp_202_Module2bypassLineVoltageCA OBJECT-TYPE
		SYNTAX Integer32
		
		MAX-ACCESS read-only
		STATUS current
		DESCRIPTION
		"upsApm160snmp_202_Module2bypassLineVoltageCA stored as 0.01V."
		::= { upsApm160snmpEntry 202 }
upsApm160snmp_203_Module2bypassFrequency OBJECT-TYPE
		SYNTAX Integer32
		
		MAX-ACCESS read-only
		STATUS current
		DESCRIPTION
		"upsApm160snmp_203_Module2bypassFrequency stored as 0.01Hz."
		::= { upsApm160snmpEntry 203 }
upsApm160snmp_204_Module2batteryRemainsTime OBJECT-TYPE
		SYNTAX Integer32
		
		MAX-ACCESS read-only
		STATUS current
		DESCRIPTION
		"upsApm160snmp_204_Module2batteryRemainsTime stored as 0.01min."
		::= { upsApm160snmpEntry 204 }
upsApm160snmp_205_Module2batteryPositiveVoltage OBJECT-TYPE
		SYNTAX Integer32
		
		MAX-ACCESS read-only
		STATUS current
		DESCRIPTION
		"upsApm160snmp_205_Module2batteryPositiveVoltage stored as 0.01V."
		::= { upsApm160snmpEntry 205 }
upsApm160snmp_206_Module2batteryPositiveCurrent OBJECT-TYPE
		SYNTAX Integer32
		
		MAX-ACCESS read-only
		STATUS current
		DESCRIPTION
		"upsApm160snmp_206_Module2batteryPositiveCurrent stored as 0.01A."
		::= { upsApm160snmpEntry 206 }
upsApm160snmp_207_Module2batteryNegativeVoltage OBJECT-TYPE
		SYNTAX Integer32
		
		MAX-ACCESS read-only
		STATUS current
		DESCRIPTION
		"upsApm160snmp_207_Module2batteryNegativeVoltage stored as 0.01V."
		::= { upsApm160snmpEntry 207 }
upsApm160snmp_208_Module2batteryNegativeCurrent OBJECT-TYPE
		SYNTAX Integer32
		
		MAX-ACCESS read-only
		STATUS current
		DESCRIPTION
		"upsApm160snmp_208_Module2batteryNegativeCurrent stored as 0.01A."
		::= { upsApm160snmpEntry 208 }
upsApm160snmp_209_Module2batteryAgingRate OBJECT-TYPE
		SYNTAX Integer32
		
		MAX-ACCESS read-only
		STATUS current
		DESCRIPTION
		"upsApm160snmp_209_Module2batteryAgingRate stored as 0.01."
		::= { upsApm160snmpEntry 209 }
upsApm160snmp_210_Module2batteryTemperature OBJECT-TYPE
		SYNTAX Integer32
		
		MAX-ACCESS read-only
		STATUS current
		DESCRIPTION
		"upsApm160snmp_210_Module2batteryTemperature stored as 0.01℃."
		::= { upsApm160snmpEntry 210 }
upsApm160snmp_211_Module3inputPhaseVoltageA OBJECT-TYPE
		SYNTAX Integer32
		
		MAX-ACCESS read-only
		STATUS current
		DESCRIPTION
		"upsApm160snmp_211_Module3inputPhaseVoltageA stored as 0.01V."
		::= { upsApm160snmpEntry 211 }
upsApm160snmp_212_Module3inputPhaseVoltageB OBJECT-TYPE
		SYNTAX Integer32
		
		MAX-ACCESS read-only
		STATUS current
		DESCRIPTION
		"upsApm160snmp_212_Module3inputPhaseVoltageB stored as 0.01V."
		::= { upsApm160snmpEntry 212 }
upsApm160snmp_213_Module3inputPhaseVoltageC OBJECT-TYPE
		SYNTAX Integer32
		
		MAX-ACCESS read-only
		STATUS current
		DESCRIPTION
		"upsApm160snmp_213_Module3inputPhaseVoltageC stored as 0.01V."
		::= { upsApm160snmpEntry 213 }
upsApm160snmp_214_Module3inputLineVoltageA OBJECT-TYPE
		SYNTAX Integer32
		
		MAX-ACCESS read-only
		STATUS current
		DESCRIPTION
		"upsApm160snmp_214_Module3inputLineVoltageA stored as 0.01V."
		::= { upsApm160snmpEntry 214 }
upsApm160snmp_215_Module3inputLineVoltageB OBJECT-TYPE
		SYNTAX Integer32
		
		MAX-ACCESS read-only
		STATUS current
		DESCRIPTION
		"upsApm160snmp_215_Module3inputLineVoltageB stored as 0.01V."
		::= { upsApm160snmpEntry 215 }
upsApm160snmp_216_Module3inputLineVoltageC OBJECT-TYPE
		SYNTAX Integer32
		
		MAX-ACCESS read-only
		STATUS current
		DESCRIPTION
		"upsApm160snmp_216_Module3inputLineVoltageC stored as 0.01V."
		::= { upsApm160snmpEntry 216 }
upsApm160snmp_217_Module3inputCurrentA OBJECT-TYPE
		SYNTAX Integer32
		
		MAX-ACCESS read-only
		STATUS current
		DESCRIPTION
		"upsApm160snmp_217_Module3inputCurrentA stored as 0.01A."
		::= { upsApm160snmpEntry 217 }
upsApm160snmp_218_Module3inputCurrentB OBJECT-TYPE
		SYNTAX Integer32
		
		MAX-ACCESS read-only
		STATUS current
		DESCRIPTION
		"upsApm160snmp_218_Module3inputCurrentB stored as 0.01A."
		::= { upsApm160snmpEntry 218 }
upsApm160snmp_219_Module3inputCurrentC OBJECT-TYPE
		SYNTAX Integer32
		
		MAX-ACCESS read-only
		STATUS current
		DESCRIPTION
		"upsApm160snmp_219_Module3inputCurrentC stored as 0.01A."
		::= { upsApm160snmpEntry 219 }
upsApm160snmp_220_Module3inputFrequency OBJECT-TYPE
		SYNTAX Integer32
		
		MAX-ACCESS read-only
		STATUS current
		DESCRIPTION
		"upsApm160snmp_220_Module3inputFrequency stored as 0.01Hz."
		::= { upsApm160snmpEntry 220 }
upsApm160snmp_221_Module3inputPowerFactorA OBJECT-TYPE
		SYNTAX Integer32
		
		MAX-ACCESS read-only
		STATUS current
		DESCRIPTION
		"upsApm160snmp_221_Module3inputPowerFactorA stored as 0.01."
		::= { upsApm160snmpEntry 221 }
upsApm160snmp_222_Module3inputPowerFactorB OBJECT-TYPE
		SYNTAX Integer32
		
		MAX-ACCESS read-only
		STATUS current
		DESCRIPTION
		"upsApm160snmp_222_Module3inputPowerFactorB stored as 0.01."
		::= { upsApm160snmpEntry 222 }
upsApm160snmp_223_Module3inputPowerFactorC OBJECT-TYPE
		SYNTAX Integer32
		
		MAX-ACCESS read-only
		STATUS current
		DESCRIPTION
		"upsApm160snmp_223_Module3inputPowerFactorC stored as 0.01."
		::= { upsApm160snmpEntry 223 }
upsApm160snmp_224_Module3batteryVoltage OBJECT-TYPE
		SYNTAX Integer32
		
		MAX-ACCESS read-only
		STATUS current
		DESCRIPTION
		"upsApm160snmp_224_Module3batteryVoltage stored as 0.01V."
		::= { upsApm160snmpEntry 224 }
upsApm160snmp_225_Module3inputActivePowerA OBJECT-TYPE
		SYNTAX Integer32
		
		MAX-ACCESS read-only
		STATUS current
		DESCRIPTION
		"upsApm160snmp_225_Module3inputActivePowerA stored as 0.01kW."
		::= { upsApm160snmpEntry 225 }
upsApm160snmp_226_Module3inputActivePowerB OBJECT-TYPE
		SYNTAX Integer32
		
		MAX-ACCESS read-only
		STATUS current
		DESCRIPTION
		"upsApm160snmp_226_Module3inputActivePowerB stored as 0.01kW."
		::= { upsApm160snmpEntry 226 }
upsApm160snmp_227_Module3inputActivePowerC OBJECT-TYPE
		SYNTAX Integer32
		
		MAX-ACCESS read-only
		STATUS current
		DESCRIPTION
		"upsApm160snmp_227_Module3inputActivePowerC stored as 0.01kW."
		::= { upsApm160snmpEntry 227 }
upsApm160snmp_228_Module3inputAppPowerA OBJECT-TYPE
		SYNTAX Integer32
		
		MAX-ACCESS read-only
		STATUS current
		DESCRIPTION
		"upsApm160snmp_228_Module3inputAppPowerA stored as 0.01kVA."
		::= { upsApm160snmpEntry 228 }
upsApm160snmp_229_Module3inputAppPowerB OBJECT-TYPE
		SYNTAX Integer32
		
		MAX-ACCESS read-only
		STATUS current
		DESCRIPTION
		"upsApm160snmp_229_Module3inputAppPowerB stored as 0.01kVA."
		::= { upsApm160snmpEntry 229 }
upsApm160snmp_230_Module3inputAppPowerC OBJECT-TYPE
		SYNTAX Integer32
		
		MAX-ACCESS read-only
		STATUS current
		DESCRIPTION
		"upsApm160snmp_230_Module3inputAppPowerC stored as 0.01kVA."
		::= { upsApm160snmpEntry 230 }
upsApm160snmp_231_Module3inputEnergyA OBJECT-TYPE
		SYNTAX Integer32
		
		MAX-ACCESS read-only
		STATUS current
		DESCRIPTION
		"upsApm160snmp_231_Module3inputEnergyA stored as 0.01kWh."
		::= { upsApm160snmpEntry 231 }
upsApm160snmp_232_Module3inputEnergyB OBJECT-TYPE
		SYNTAX Integer32
		
		MAX-ACCESS read-only
		STATUS current
		DESCRIPTION
		"upsApm160snmp_232_Module3inputEnergyB stored as 0.01kWh."
		::= { upsApm160snmpEntry 232 }
upsApm160snmp_233_Module3inputEnergyC OBJECT-TYPE
		SYNTAX Integer32
		
		MAX-ACCESS read-only
		STATUS current
		DESCRIPTION
		"upsApm160snmp_233_Module3inputEnergyC stored as 0.01kWh."
		::= { upsApm160snmpEntry 233 }
upsApm160snmp_234_Module3outputVoltageA OBJECT-TYPE
		SYNTAX Integer32
		
		MAX-ACCESS read-only
		STATUS current
		DESCRIPTION
		"upsApm160snmp_234_Module3outputVoltageA stored as 0.01V."
		::= { upsApm160snmpEntry 234 }
upsApm160snmp_235_Module3outputVoltageB OBJECT-TYPE
		SYNTAX Integer32
		
		MAX-ACCESS read-only
		STATUS current
		DESCRIPTION
		"upsApm160snmp_235_Module3outputVoltageB stored as 0.01V."
		::= { upsApm160snmpEntry 235 }
upsApm160snmp_236_Module3outputVoltageC OBJECT-TYPE
		SYNTAX Integer32
		
		MAX-ACCESS read-only
		STATUS current
		DESCRIPTION
		"upsApm160snmp_236_Module3outputVoltageC stored as 0.01V."
		::= { upsApm160snmpEntry 236 }
upsApm160snmp_237_Module3outputLineVoltageAB OBJECT-TYPE
		SYNTAX Integer32
		
		MAX-ACCESS read-only
		STATUS current
		DESCRIPTION
		"upsApm160snmp_237_Module3outputLineVoltageAB stored as 0.01V."
		::= { upsApm160snmpEntry 237 }
upsApm160snmp_238_Module3outputLineVoltageBC OBJECT-TYPE
		SYNTAX Integer32
		
		MAX-ACCESS read-only
		STATUS current
		DESCRIPTION
		"upsApm160snmp_238_Module3outputLineVoltageBC stored as 0.01V."
		::= { upsApm160snmpEntry 238 }
upsApm160snmp_239_Module3outputLineVoltageCA OBJECT-TYPE
		SYNTAX Integer32
		
		MAX-ACCESS read-only
		STATUS current
		DESCRIPTION
		"upsApm160snmp_239_Module3outputLineVoltageCA stored as 0.01V."
		::= { upsApm160snmpEntry 239 }
upsApm160snmp_240_Module3outputCurrentA OBJECT-TYPE
		SYNTAX Integer32
		
		MAX-ACCESS read-only
		STATUS current
		DESCRIPTION
		"upsApm160snmp_240_Module3outputCurrentA stored as 0.01A."
		::= { upsApm160snmpEntry 240 }
upsApm160snmp_241_Module3outputCurrentB OBJECT-TYPE
		SYNTAX Integer32
		
		MAX-ACCESS read-only
		STATUS current
		DESCRIPTION
		"upsApm160snmp_241_Module3outputCurrentB stored as 0.01A."
		::= { upsApm160snmpEntry 241 }
upsApm160snmp_242_Module3outputCurrentC OBJECT-TYPE
		SYNTAX Integer32
		
		MAX-ACCESS read-only
		STATUS current
		DESCRIPTION
		"upsApm160snmp_242_Module3outputCurrentC stored as 0.01A."
		::= { upsApm160snmpEntry 242 }
upsApm160snmp_243_Module3outputFrequency OBJECT-TYPE
		SYNTAX Integer32
		
		MAX-ACCESS read-only
		STATUS current
		DESCRIPTION
		"upsApm160snmp_243_Module3outputFrequency stored as 0.01Hz."
		::= { upsApm160snmpEntry 243 }
upsApm160snmp_244_Module3outputPowerFactorA OBJECT-TYPE
		SYNTAX Integer32
		
		MAX-ACCESS read-only
		STATUS current
		DESCRIPTION
		"upsApm160snmp_244_Module3outputPowerFactorA stored as 0.01."
		::= { upsApm160snmpEntry 244 }
upsApm160snmp_245_Module3outputPowerFactorB OBJECT-TYPE
		SYNTAX Integer32
		
		MAX-ACCESS read-only
		STATUS current
		DESCRIPTION
		"upsApm160snmp_245_Module3outputPowerFactorB stored as 0.01."
		::= { upsApm160snmpEntry 245 }
upsApm160snmp_246_Module3outputPowerFactorC OBJECT-TYPE
		SYNTAX Integer32
		
		MAX-ACCESS read-only
		STATUS current
		DESCRIPTION
		"upsApm160snmp_246_Module3outputPowerFactorC stored as 0.01."
		::= { upsApm160snmpEntry 246 }
upsApm160snmp_247_Module3outputAcitvePowerA OBJECT-TYPE
		SYNTAX Integer32
		
		MAX-ACCESS read-only
		STATUS current
		DESCRIPTION
		"upsApm160snmp_247_Module3outputAcitvePowerA stored as 0.01kW."
		::= { upsApm160snmpEntry 247 }
upsApm160snmp_248_Module3outputAcitvePowerB OBJECT-TYPE
		SYNTAX Integer32
		
		MAX-ACCESS read-only
		STATUS current
		DESCRIPTION
		"upsApm160snmp_248_Module3outputAcitvePowerB stored as 0.01kW."
		::= { upsApm160snmpEntry 248 }
upsApm160snmp_249_Module3outputAcitvePowerC OBJECT-TYPE
		SYNTAX Integer32
		
		MAX-ACCESS read-only
		STATUS current
		DESCRIPTION
		"upsApm160snmp_249_Module3outputAcitvePowerC stored as 0.01kW."
		::= { upsApm160snmpEntry 249 }
upsApm160snmp_250_Module3outputReactivePowerA OBJECT-TYPE
		SYNTAX Integer32
		
		MAX-ACCESS read-only
		STATUS current
		DESCRIPTION
		"upsApm160snmp_250_Module3outputReactivePowerA stored as 0.01kVar."
		::= { upsApm160snmpEntry 250 }
upsApm160snmp_251_Module3outputReactivePowerB OBJECT-TYPE
		SYNTAX Integer32
		
		MAX-ACCESS read-only
		STATUS current
		DESCRIPTION
		"upsApm160snmp_251_Module3outputReactivePowerB stored as 0.01kVar."
		::= { upsApm160snmpEntry 251 }
upsApm160snmp_252_Module3outputReactivePowerC OBJECT-TYPE
		SYNTAX Integer32
		
		MAX-ACCESS read-only
		STATUS current
		DESCRIPTION
		"upsApm160snmp_252_Module3outputReactivePowerC stored as 0.01kVar."
		::= { upsApm160snmpEntry 252 }
upsApm160snmp_253_Module3outputAppPowerA OBJECT-TYPE
		SYNTAX Integer32
		
		MAX-ACCESS read-only
		STATUS current
		DESCRIPTION
		"upsApm160snmp_253_Module3outputAppPowerA stored as 0.01kVA."
		::= { upsApm160snmpEntry 253 }
upsApm160snmp_254_Module3outputAppPowerB OBJECT-TYPE
		SYNTAX Integer32
		
		MAX-ACCESS read-only
		STATUS current
		DESCRIPTION
		"upsApm160snmp_254_Module3outputAppPowerB stored as 0.01kVA."
		::= { upsApm160snmpEntry 254 }
upsApm160snmp_255_Module3outputAppPowerC OBJECT-TYPE
		SYNTAX Integer32
		
		MAX-ACCESS read-only
		STATUS current
		DESCRIPTION
		"upsApm160snmp_255_Module3outputAppPowerC stored as 0.01kVA."
		::= { upsApm160snmpEntry 255 }
upsApm160snmp_256_Module3outputLoadA OBJECT-TYPE
		SYNTAX Integer32
		
		MAX-ACCESS read-only
		STATUS current
		DESCRIPTION
		"upsApm160snmp_256_Module3outputLoadA stored as 0.01%."
		::= { upsApm160snmpEntry 256 }
upsApm160snmp_257_Module3outputLoadB OBJECT-TYPE
		SYNTAX Integer32
		
		MAX-ACCESS read-only
		STATUS current
		DESCRIPTION
		"upsApm160snmp_257_Module3outputLoadB stored as 0.01%."
		::= { upsApm160snmpEntry 257 }
upsApm160snmp_258_Module3outputLoadC OBJECT-TYPE
		SYNTAX Integer32
		
		MAX-ACCESS read-only
		STATUS current
		DESCRIPTION
		"upsApm160snmp_258_Module3outputLoadC stored as 0.01%."
		::= { upsApm160snmpEntry 258 }
upsApm160snmp_259_Module3outputCrestFactorA OBJECT-TYPE
		SYNTAX Integer32
		
		MAX-ACCESS read-only
		STATUS current
		DESCRIPTION
		"upsApm160snmp_259_Module3outputCrestFactorA stored as 0.01."
		::= { upsApm160snmpEntry 259 }
upsApm160snmp_260_Module3outputCrestFactorB OBJECT-TYPE
		SYNTAX Integer32
		
		MAX-ACCESS read-only
		STATUS current
		DESCRIPTION
		"upsApm160snmp_260_Module3outputCrestFactorB stored as 0.01."
		::= { upsApm160snmpEntry 260 }
upsApm160snmp_261_Module3outputCrestFactorC OBJECT-TYPE
		SYNTAX Integer32
		
		MAX-ACCESS read-only
		STATUS current
		DESCRIPTION
		"upsApm160snmp_261_Module3outputCrestFactorC stored as 0.01."
		::= { upsApm160snmpEntry 261 }
upsApm160snmp_262_Module3bypassVoltageA OBJECT-TYPE
		SYNTAX Integer32
		
		MAX-ACCESS read-only
		STATUS current
		DESCRIPTION
		"upsApm160snmp_262_Module3bypassVoltageA stored as 0.01V."
		::= { upsApm160snmpEntry 262 }
upsApm160snmp_263_Module3bypassVoltageB OBJECT-TYPE
		SYNTAX Integer32
		
		MAX-ACCESS read-only
		STATUS current
		DESCRIPTION
		"upsApm160snmp_263_Module3bypassVoltageB stored as 0.01V."
		::= { upsApm160snmpEntry 263 }
upsApm160snmp_264_Module3bypassVoltageC OBJECT-TYPE
		SYNTAX Integer32
		
		MAX-ACCESS read-only
		STATUS current
		DESCRIPTION
		"upsApm160snmp_264_Module3bypassVoltageC stored as 0.01V."
		::= { upsApm160snmpEntry 264 }
upsApm160snmp_265_Module3bypassLineVoltageAB OBJECT-TYPE
		SYNTAX Integer32
		
		MAX-ACCESS read-only
		STATUS current
		DESCRIPTION
		"upsApm160snmp_265_Module3bypassLineVoltageAB stored as 0.01V."
		::= { upsApm160snmpEntry 265 }
upsApm160snmp_266_Module3bypassLineVoltageBC OBJECT-TYPE
		SYNTAX Integer32
		
		MAX-ACCESS read-only
		STATUS current
		DESCRIPTION
		"upsApm160snmp_266_Module3bypassLineVoltageBC stored as 0.01V."
		::= { upsApm160snmpEntry 266 }
upsApm160snmp_267_Module3bypassLineVoltageCA OBJECT-TYPE
		SYNTAX Integer32
		
		MAX-ACCESS read-only
		STATUS current
		DESCRIPTION
		"upsApm160snmp_267_Module3bypassLineVoltageCA stored as 0.01V."
		::= { upsApm160snmpEntry 267 }
upsApm160snmp_268_Module3bypassFrequency OBJECT-TYPE
		SYNTAX Integer32
		
		MAX-ACCESS read-only
		STATUS current
		DESCRIPTION
		"upsApm160snmp_268_Module3bypassFrequency stored as 0.01Hz."
		::= { upsApm160snmpEntry 268 }
upsApm160snmp_269_Module3batteryRemainsTime OBJECT-TYPE
		SYNTAX Integer32
		
		MAX-ACCESS read-only
		STATUS current
		DESCRIPTION
		"upsApm160snmp_269_Module3batteryRemainsTime stored as 0.01min."
		::= { upsApm160snmpEntry 269 }
upsApm160snmp_270_Module3batteryPositiveVoltage OBJECT-TYPE
		SYNTAX Integer32
		
		MAX-ACCESS read-only
		STATUS current
		DESCRIPTION
		"upsApm160snmp_270_Module3batteryPositiveVoltage stored as 0.01V."
		::= { upsApm160snmpEntry 270 }
upsApm160snmp_271_Module3batteryPositiveCurrent OBJECT-TYPE
		SYNTAX Integer32
		
		MAX-ACCESS read-only
		STATUS current
		DESCRIPTION
		"upsApm160snmp_271_Module3batteryPositiveCurrent stored as 0.01A."
		::= { upsApm160snmpEntry 271 }
upsApm160snmp_272_Module3batteryNegativeVoltage OBJECT-TYPE
		SYNTAX Integer32
		
		MAX-ACCESS read-only
		STATUS current
		DESCRIPTION
		"upsApm160snmp_272_Module3batteryNegativeVoltage stored as 0.01V."
		::= { upsApm160snmpEntry 272 }
upsApm160snmp_273_Module3batteryNegativeCurrent OBJECT-TYPE
		SYNTAX Integer32
		
		MAX-ACCESS read-only
		STATUS current
		DESCRIPTION
		"upsApm160snmp_273_Module3batteryNegativeCurrent stored as 0.01A."
		::= { upsApm160snmpEntry 273 }
upsApm160snmp_274_Module3batteryAgingRate OBJECT-TYPE
		SYNTAX Integer32
		
		MAX-ACCESS read-only
		STATUS current
		DESCRIPTION
		"upsApm160snmp_274_Module3batteryAgingRate stored as 0.01."
		::= { upsApm160snmpEntry 274 }
upsApm160snmp_275_Module3batteryTemperature OBJECT-TYPE
		SYNTAX Integer32
		
		MAX-ACCESS read-only
		STATUS current
		DESCRIPTION
		"upsApm160snmp_275_Module3batteryTemperature stored as 0.01℃."
		::= { upsApm160snmpEntry 275 }
upsApm160snmp_276_Module4inputPhaseVoltageA OBJECT-TYPE
		SYNTAX Integer32
		
		MAX-ACCESS read-only
		STATUS current
		DESCRIPTION
		"upsApm160snmp_276_Module4inputPhaseVoltageA stored as 0.01V."
		::= { upsApm160snmpEntry 276 }
upsApm160snmp_277_Module4inputPhaseVoltageB OBJECT-TYPE
		SYNTAX Integer32
		
		MAX-ACCESS read-only
		STATUS current
		DESCRIPTION
		"upsApm160snmp_277_Module4inputPhaseVoltageB stored as 0.01V."
		::= { upsApm160snmpEntry 277 }
upsApm160snmp_278_Module4inputPhaseVoltageC OBJECT-TYPE
		SYNTAX Integer32
		
		MAX-ACCESS read-only
		STATUS current
		DESCRIPTION
		"upsApm160snmp_278_Module4inputPhaseVoltageC stored as 0.01V."
		::= { upsApm160snmpEntry 278 }
upsApm160snmp_279_Module4inputLineVoltageA OBJECT-TYPE
		SYNTAX Integer32
		
		MAX-ACCESS read-only
		STATUS current
		DESCRIPTION
		"upsApm160snmp_279_Module4inputLineVoltageA stored as 0.01V."
		::= { upsApm160snmpEntry 279 }
upsApm160snmp_280_Module4inputLineVoltageB OBJECT-TYPE
		SYNTAX Integer32
		
		MAX-ACCESS read-only
		STATUS current
		DESCRIPTION
		"upsApm160snmp_280_Module4inputLineVoltageB stored as 0.01V."
		::= { upsApm160snmpEntry 280 }
upsApm160snmp_281_Module4inputLineVoltageC OBJECT-TYPE
		SYNTAX Integer32
		
		MAX-ACCESS read-only
		STATUS current
		DESCRIPTION
		"upsApm160snmp_281_Module4inputLineVoltageC stored as 0.01V."
		::= { upsApm160snmpEntry 281 }
upsApm160snmp_282_Module4inputCurrentA OBJECT-TYPE
		SYNTAX Integer32
		
		MAX-ACCESS read-only
		STATUS current
		DESCRIPTION
		"upsApm160snmp_282_Module4inputCurrentA stored as 0.01A."
		::= { upsApm160snmpEntry 282 }
upsApm160snmp_283_Module4inputCurrentB OBJECT-TYPE
		SYNTAX Integer32
		
		MAX-ACCESS read-only
		STATUS current
		DESCRIPTION
		"upsApm160snmp_283_Module4inputCurrentB stored as 0.01A."
		::= { upsApm160snmpEntry 283 }
upsApm160snmp_284_Module4inputCurrentC OBJECT-TYPE
		SYNTAX Integer32
		
		MAX-ACCESS read-only
		STATUS current
		DESCRIPTION
		"upsApm160snmp_284_Module4inputCurrentC stored as 0.01A."
		::= { upsApm160snmpEntry 284 }
upsApm160snmp_285_Module4inputFrequency OBJECT-TYPE
		SYNTAX Integer32
		
		MAX-ACCESS read-only
		STATUS current
		DESCRIPTION
		"upsApm160snmp_285_Module4inputFrequency stored as 0.01Hz."
		::= { upsApm160snmpEntry 285 }
upsApm160snmp_286_Module4inputPowerFactorA OBJECT-TYPE
		SYNTAX Integer32
		
		MAX-ACCESS read-only
		STATUS current
		DESCRIPTION
		"upsApm160snmp_286_Module4inputPowerFactorA stored as 0.01."
		::= { upsApm160snmpEntry 286 }
upsApm160snmp_287_Module4inputPowerFactorB OBJECT-TYPE
		SYNTAX Integer32
		
		MAX-ACCESS read-only
		STATUS current
		DESCRIPTION
		"upsApm160snmp_287_Module4inputPowerFactorB stored as 0.01."
		::= { upsApm160snmpEntry 287 }
upsApm160snmp_288_Module4inputPowerFactorC OBJECT-TYPE
		SYNTAX Integer32
		
		MAX-ACCESS read-only
		STATUS current
		DESCRIPTION
		"upsApm160snmp_288_Module4inputPowerFactorC stored as 0.01."
		::= { upsApm160snmpEntry 288 }
upsApm160snmp_289_Module4batteryVoltage OBJECT-TYPE
		SYNTAX Integer32
		
		MAX-ACCESS read-only
		STATUS current
		DESCRIPTION
		"upsApm160snmp_289_Module4batteryVoltage stored as 0.01V."
		::= { upsApm160snmpEntry 289 }
upsApm160snmp_290_Module4inputActivePowerA OBJECT-TYPE
		SYNTAX Integer32
		
		MAX-ACCESS read-only
		STATUS current
		DESCRIPTION
		"upsApm160snmp_290_Module4inputActivePowerA stored as 0.01kW."
		::= { upsApm160snmpEntry 290 }
upsApm160snmp_291_Module4inputActivePowerB OBJECT-TYPE
		SYNTAX Integer32
		
		MAX-ACCESS read-only
		STATUS current
		DESCRIPTION
		"upsApm160snmp_291_Module4inputActivePowerB stored as 0.01kW."
		::= { upsApm160snmpEntry 291 }
upsApm160snmp_292_Module4inputActivePowerC OBJECT-TYPE
		SYNTAX Integer32
		
		MAX-ACCESS read-only
		STATUS current
		DESCRIPTION
		"upsApm160snmp_292_Module4inputActivePowerC stored as 0.01kW."
		::= { upsApm160snmpEntry 292 }
upsApm160snmp_293_Module4inputAppPowerA OBJECT-TYPE
		SYNTAX Integer32
		
		MAX-ACCESS read-only
		STATUS current
		DESCRIPTION
		"upsApm160snmp_293_Module4inputAppPowerA stored as 0.01kVA."
		::= { upsApm160snmpEntry 293 }
upsApm160snmp_294_Module4inputAppPowerB OBJECT-TYPE
		SYNTAX Integer32
		
		MAX-ACCESS read-only
		STATUS current
		DESCRIPTION
		"upsApm160snmp_294_Module4inputAppPowerB stored as 0.01kVA."
		::= { upsApm160snmpEntry 294 }
upsApm160snmp_295_Module4inputAppPowerC OBJECT-TYPE
		SYNTAX Integer32
		
		MAX-ACCESS read-only
		STATUS current
		DESCRIPTION
		"upsApm160snmp_295_Module4inputAppPowerC stored as 0.01kVA."
		::= { upsApm160snmpEntry 295 }
upsApm160snmp_296_Module4inputEnergyA OBJECT-TYPE
		SYNTAX Integer32
		
		MAX-ACCESS read-only
		STATUS current
		DESCRIPTION
		"upsApm160snmp_296_Module4inputEnergyA stored as 0.01kWh."
		::= { upsApm160snmpEntry 296 }
upsApm160snmp_297_Module4inputEnergyB OBJECT-TYPE
		SYNTAX Integer32
		
		MAX-ACCESS read-only
		STATUS current
		DESCRIPTION
		"upsApm160snmp_297_Module4inputEnergyB stored as 0.01kWh."
		::= { upsApm160snmpEntry 297 }
upsApm160snmp_298_Module4inputEnergyC OBJECT-TYPE
		SYNTAX Integer32
		
		MAX-ACCESS read-only
		STATUS current
		DESCRIPTION
		"upsApm160snmp_298_Module4inputEnergyC stored as 0.01kWh."
		::= { upsApm160snmpEntry 298 }
upsApm160snmp_299_Module4outputVoltageA OBJECT-TYPE
		SYNTAX Integer32
		
		MAX-ACCESS read-only
		STATUS current
		DESCRIPTION
		"upsApm160snmp_299_Module4outputVoltageA stored as 0.01V."
		::= { upsApm160snmpEntry 299 }
upsApm160snmp_300_Module4outputVoltageB OBJECT-TYPE
		SYNTAX Integer32
		
		MAX-ACCESS read-only
		STATUS current
		DESCRIPTION
		"upsApm160snmp_300_Module4outputVoltageB stored as 0.01V."
		::= { upsApm160snmpEntry 300 }
upsApm160snmp_301_Module4outputVoltageC OBJECT-TYPE
		SYNTAX Integer32
		
		MAX-ACCESS read-only
		STATUS current
		DESCRIPTION
		"upsApm160snmp_301_Module4outputVoltageC stored as 0.01V."
		::= { upsApm160snmpEntry 301 }
upsApm160snmp_302_Module4outputLineVoltageAB OBJECT-TYPE
		SYNTAX Integer32
		
		MAX-ACCESS read-only
		STATUS current
		DESCRIPTION
		"upsApm160snmp_302_Module4outputLineVoltageAB stored as 0.01V."
		::= { upsApm160snmpEntry 302 }
upsApm160snmp_303_Module4outputLineVoltageBC OBJECT-TYPE
		SYNTAX Integer32
		
		MAX-ACCESS read-only
		STATUS current
		DESCRIPTION
		"upsApm160snmp_303_Module4outputLineVoltageBC stored as 0.01V."
		::= { upsApm160snmpEntry 303 }
upsApm160snmp_304_Module4outputLineVoltageCA OBJECT-TYPE
		SYNTAX Integer32
		
		MAX-ACCESS read-only
		STATUS current
		DESCRIPTION
		"upsApm160snmp_304_Module4outputLineVoltageCA stored as 0.01V."
		::= { upsApm160snmpEntry 304 }
upsApm160snmp_305_Module4outputCurrentA OBJECT-TYPE
		SYNTAX Integer32
		
		MAX-ACCESS read-only
		STATUS current
		DESCRIPTION
		"upsApm160snmp_305_Module4outputCurrentA stored as 0.01A."
		::= { upsApm160snmpEntry 305 }
upsApm160snmp_306_Module4outputCurrentB OBJECT-TYPE
		SYNTAX Integer32
		
		MAX-ACCESS read-only
		STATUS current
		DESCRIPTION
		"upsApm160snmp_306_Module4outputCurrentB stored as 0.01A."
		::= { upsApm160snmpEntry 306 }
upsApm160snmp_307_Module4outputCurrentC OBJECT-TYPE
		SYNTAX Integer32
		
		MAX-ACCESS read-only
		STATUS current
		DESCRIPTION
		"upsApm160snmp_307_Module4outputCurrentC stored as 0.01A."
		::= { upsApm160snmpEntry 307 }
upsApm160snmp_308_Module4outputFrequency OBJECT-TYPE
		SYNTAX Integer32
		
		MAX-ACCESS read-only
		STATUS current
		DESCRIPTION
		"upsApm160snmp_308_Module4outputFrequency stored as 0.01Hz."
		::= { upsApm160snmpEntry 308 }
upsApm160snmp_309_Module4outputPowerFactorA OBJECT-TYPE
		SYNTAX Integer32
		
		MAX-ACCESS read-only
		STATUS current
		DESCRIPTION
		"upsApm160snmp_309_Module4outputPowerFactorA stored as 0.01."
		::= { upsApm160snmpEntry 309 }
upsApm160snmp_310_Module4outputPowerFactorB OBJECT-TYPE
		SYNTAX Integer32
		
		MAX-ACCESS read-only
		STATUS current
		DESCRIPTION
		"upsApm160snmp_310_Module4outputPowerFactorB stored as 0.01."
		::= { upsApm160snmpEntry 310 }
upsApm160snmp_311_Module4outputPowerFactorC OBJECT-TYPE
		SYNTAX Integer32
		
		MAX-ACCESS read-only
		STATUS current
		DESCRIPTION
		"upsApm160snmp_311_Module4outputPowerFactorC stored as 0.01."
		::= { upsApm160snmpEntry 311 }
upsApm160snmp_312_Module4outputAcitvePowerA OBJECT-TYPE
		SYNTAX Integer32
		
		MAX-ACCESS read-only
		STATUS current
		DESCRIPTION
		"upsApm160snmp_312_Module4outputAcitvePowerA stored as 0.01kW."
		::= { upsApm160snmpEntry 312 }
upsApm160snmp_313_Module4outputAcitvePowerB OBJECT-TYPE
		SYNTAX Integer32
		
		MAX-ACCESS read-only
		STATUS current
		DESCRIPTION
		"upsApm160snmp_313_Module4outputAcitvePowerB stored as 0.01kW."
		::= { upsApm160snmpEntry 313 }
upsApm160snmp_314_Module4outputAcitvePowerC OBJECT-TYPE
		SYNTAX Integer32
		
		MAX-ACCESS read-only
		STATUS current
		DESCRIPTION
		"upsApm160snmp_314_Module4outputAcitvePowerC stored as 0.01kW."
		::= { upsApm160snmpEntry 314 }
upsApm160snmp_315_Module4outputReactivePowerA OBJECT-TYPE
		SYNTAX Integer32
		
		MAX-ACCESS read-only
		STATUS current
		DESCRIPTION
		"upsApm160snmp_315_Module4outputReactivePowerA stored as 0.01kVar."
		::= { upsApm160snmpEntry 315 }
upsApm160snmp_316_Module4outputReactivePowerB OBJECT-TYPE
		SYNTAX Integer32
		
		MAX-ACCESS read-only
		STATUS current
		DESCRIPTION
		"upsApm160snmp_316_Module4outputReactivePowerB stored as 0.01kVar."
		::= { upsApm160snmpEntry 316 }
upsApm160snmp_317_Module4outputReactivePowerC OBJECT-TYPE
		SYNTAX Integer32
		
		MAX-ACCESS read-only
		STATUS current
		DESCRIPTION
		"upsApm160snmp_317_Module4outputReactivePowerC stored as 0.01kVar."
		::= { upsApm160snmpEntry 317 }
upsApm160snmp_318_Module4outputAppPowerA OBJECT-TYPE
		SYNTAX Integer32
		
		MAX-ACCESS read-only
		STATUS current
		DESCRIPTION
		"upsApm160snmp_318_Module4outputAppPowerA stored as 0.01kVA."
		::= { upsApm160snmpEntry 318 }
upsApm160snmp_319_Module4outputAppPowerB OBJECT-TYPE
		SYNTAX Integer32
		
		MAX-ACCESS read-only
		STATUS current
		DESCRIPTION
		"upsApm160snmp_319_Module4outputAppPowerB stored as 0.01kVA."
		::= { upsApm160snmpEntry 319 }
upsApm160snmp_320_Module4outputAppPowerC OBJECT-TYPE
		SYNTAX Integer32
		
		MAX-ACCESS read-only
		STATUS current
		DESCRIPTION
		"upsApm160snmp_320_Module4outputAppPowerC stored as 0.01kVA."
		::= { upsApm160snmpEntry 320 }
upsApm160snmp_321_Module4outputLoadA OBJECT-TYPE
		SYNTAX Integer32
		
		MAX-ACCESS read-only
		STATUS current
		DESCRIPTION
		"upsApm160snmp_321_Module4outputLoadA stored as 0.01%."
		::= { upsApm160snmpEntry 321 }
upsApm160snmp_322_Module4outputLoadB OBJECT-TYPE
		SYNTAX Integer32
		
		MAX-ACCESS read-only
		STATUS current
		DESCRIPTION
		"upsApm160snmp_322_Module4outputLoadB stored as 0.01%."
		::= { upsApm160snmpEntry 322 }
upsApm160snmp_323_Module4outputLoadC OBJECT-TYPE
		SYNTAX Integer32
		
		MAX-ACCESS read-only
		STATUS current
		DESCRIPTION
		"upsApm160snmp_323_Module4outputLoadC stored as 0.01%."
		::= { upsApm160snmpEntry 323 }
upsApm160snmp_324_Module4outputCrestFactorA OBJECT-TYPE
		SYNTAX Integer32
		
		MAX-ACCESS read-only
		STATUS current
		DESCRIPTION
		"upsApm160snmp_324_Module4outputCrestFactorA stored as 0.01."
		::= { upsApm160snmpEntry 324 }
upsApm160snmp_325_Module4outputCrestFactorB OBJECT-TYPE
		SYNTAX Integer32
		
		MAX-ACCESS read-only
		STATUS current
		DESCRIPTION
		"upsApm160snmp_325_Module4outputCrestFactorB stored as 0.01."
		::= { upsApm160snmpEntry 325 }
upsApm160snmp_326_Module4outputCrestFactorC OBJECT-TYPE
		SYNTAX Integer32
		
		MAX-ACCESS read-only
		STATUS current
		DESCRIPTION
		"upsApm160snmp_326_Module4outputCrestFactorC stored as 0.01."
		::= { upsApm160snmpEntry 326 }
upsApm160snmp_327_Module4bypassVoltageA OBJECT-TYPE
		SYNTAX Integer32
		
		MAX-ACCESS read-only
		STATUS current
		DESCRIPTION
		"upsApm160snmp_327_Module4bypassVoltageA stored as 0.01V."
		::= { upsApm160snmpEntry 327 }
upsApm160snmp_328_Module4bypassVoltageB OBJECT-TYPE
		SYNTAX Integer32
		
		MAX-ACCESS read-only
		STATUS current
		DESCRIPTION
		"upsApm160snmp_328_Module4bypassVoltageB stored as 0.01V."
		::= { upsApm160snmpEntry 328 }
upsApm160snmp_329_Module4bypassVoltageC OBJECT-TYPE
		SYNTAX Integer32
		
		MAX-ACCESS read-only
		STATUS current
		DESCRIPTION
		"upsApm160snmp_329_Module4bypassVoltageC stored as 0.01V."
		::= { upsApm160snmpEntry 329 }
upsApm160snmp_330_Module4bypassLineVoltageAB OBJECT-TYPE
		SYNTAX Integer32
		
		MAX-ACCESS read-only
		STATUS current
		DESCRIPTION
		"upsApm160snmp_330_Module4bypassLineVoltageAB stored as 0.01V."
		::= { upsApm160snmpEntry 330 }
upsApm160snmp_331_Module4bypassLineVoltageBC OBJECT-TYPE
		SYNTAX Integer32
		
		MAX-ACCESS read-only
		STATUS current
		DESCRIPTION
		"upsApm160snmp_331_Module4bypassLineVoltageBC stored as 0.01V."
		::= { upsApm160snmpEntry 331 }
upsApm160snmp_332_Module4bypassLineVoltageCA OBJECT-TYPE
		SYNTAX Integer32
		
		MAX-ACCESS read-only
		STATUS current
		DESCRIPTION
		"upsApm160snmp_332_Module4bypassLineVoltageCA stored as 0.01V."
		::= { upsApm160snmpEntry 332 }
upsApm160snmp_333_Module4bypassFrequency OBJECT-TYPE
		SYNTAX Integer32
		
		MAX-ACCESS read-only
		STATUS current
		DESCRIPTION
		"upsApm160snmp_333_Module4bypassFrequency stored as 0.01Hz."
		::= { upsApm160snmpEntry 333 }
upsApm160snmp_334_Module4batteryRemainsTime OBJECT-TYPE
		SYNTAX Integer32
		
		MAX-ACCESS read-only
		STATUS current
		DESCRIPTION
		"upsApm160snmp_334_Module4batteryRemainsTime stored as 0.01min."
		::= { upsApm160snmpEntry 334 }
upsApm160snmp_335_Module4batteryPositiveVoltage OBJECT-TYPE
		SYNTAX Integer32
		
		MAX-ACCESS read-only
		STATUS current
		DESCRIPTION
		"upsApm160snmp_335_Module4batteryPositiveVoltage stored as 0.01V."
		::= { upsApm160snmpEntry 335 }
upsApm160snmp_336_Module4batteryPositiveCurrent OBJECT-TYPE
		SYNTAX Integer32
		
		MAX-ACCESS read-only
		STATUS current
		DESCRIPTION
		"upsApm160snmp_336_Module4batteryPositiveCurrent stored as 0.01A."
		::= { upsApm160snmpEntry 336 }
upsApm160snmp_337_Module4batteryNegativeVoltage OBJECT-TYPE
		SYNTAX Integer32
		
		MAX-ACCESS read-only
		STATUS current
		DESCRIPTION
		"upsApm160snmp_337_Module4batteryNegativeVoltage stored as 0.01V."
		::= { upsApm160snmpEntry 337 }
upsApm160snmp_338_Module4batteryNegativeCurrent OBJECT-TYPE
		SYNTAX Integer32
		
		MAX-ACCESS read-only
		STATUS current
		DESCRIPTION
		"upsApm160snmp_338_Module4batteryNegativeCurrent stored as 0.01A."
		::= { upsApm160snmpEntry 338 }
upsApm160snmp_339_Module4batteryAgingRate OBJECT-TYPE
		SYNTAX Integer32
		
		MAX-ACCESS read-only
		STATUS current
		DESCRIPTION
		"upsApm160snmp_339_Module4batteryAgingRate stored as 0.01."
		::= { upsApm160snmpEntry 339 }
upsApm160snmp_340_Module4batteryTemperature OBJECT-TYPE
		SYNTAX Integer32
		
		MAX-ACCESS read-only
		STATUS current
		DESCRIPTION
		"upsApm160snmp_340_Module4batteryTemperature stored as 0.01℃."
		::= { upsApm160snmpEntry 340 }
upsApm160snmp_341_Branch1Current OBJECT-TYPE
		SYNTAX Integer32
		
		MAX-ACCESS read-only
		STATUS current
		DESCRIPTION
		"upsApm160snmp_341_Branch1Current stored as 0.01A."
		::= { upsApm160snmpEntry 341 }
upsApm160snmp_342_Branch1Energy OBJECT-TYPE
		SYNTAX Integer32
		
		MAX-ACCESS read-only
		STATUS current
		DESCRIPTION
		"upsApm160snmp_342_Branch1Energy stored as 0.01kWh."
		::= { upsApm160snmpEntry 342 }
upsApm160snmp_343_Branch1SwitchStatus OBJECT-TYPE
		SYNTAX INTEGER {
			open(0),
			close(1) }
		MAX-ACCESS read-only
		STATUS current
		DESCRIPTION
		"upsApm160snmp_343_Branch1SwitchStatus status."
		::= { upsApm160snmpEntry 343 }
upsApm160snmp_344_Branch1ActivePower OBJECT-TYPE
		SYNTAX Integer32
		
		MAX-ACCESS read-only
		STATUS current
		DESCRIPTION
		"upsApm160snmp_344_Branch1ActivePower stored as 0.01kW."
		::= { upsApm160snmpEntry 344 }
upsApm160snmp_345_Branch1ApparentPower OBJECT-TYPE
		SYNTAX Integer32
		
		MAX-ACCESS read-only
		STATUS current
		DESCRIPTION
		"upsApm160snmp_345_Branch1ApparentPower stored as 0.01kVA."
		::= { upsApm160snmpEntry 345 }
upsApm160snmp_346_Branch1THDi OBJECT-TYPE
		SYNTAX Integer32
		
		MAX-ACCESS read-only
		STATUS current
		DESCRIPTION
		"upsApm160snmp_346_Branch1THDi stored as 0.01%."
		::= { upsApm160snmpEntry 346 }
upsApm160snmp_347_Branch1RatedCurrent OBJECT-TYPE
		SYNTAX Integer32
		
		MAX-ACCESS read-only
		STATUS current
		DESCRIPTION
		"upsApm160snmp_347_Branch1RatedCurrent stored as 0.01A."
		::= { upsApm160snmpEntry 347 }
upsApm160snmp_348_Branch1LoadRatio OBJECT-TYPE
		SYNTAX Integer32
		
		MAX-ACCESS read-only
		STATUS current
		DESCRIPTION
		"upsApm160snmp_348_Branch1LoadRatio stored as 0.01%."
		::= { upsApm160snmpEntry 348 }
upsApm160snmp_349_Branch1PowerFactor OBJECT-TYPE
		SYNTAX Integer32
		
		MAX-ACCESS read-only
		STATUS current
		DESCRIPTION
		"upsApm160snmp_349_Branch1PowerFactor stored as 0.01."
		::= { upsApm160snmpEntry 349 }
upsApm160snmp_350_Branch1Voltage OBJECT-TYPE
		SYNTAX Integer32
		
		MAX-ACCESS read-only
		STATUS current
		DESCRIPTION
		"upsApm160snmp_350_Branch1Voltage stored as 0.01V."
		::= { upsApm160snmpEntry 350 }
upsApm160snmp_351_Branch2Current OBJECT-TYPE
		SYNTAX Integer32
		
		MAX-ACCESS read-only
		STATUS current
		DESCRIPTION
		"upsApm160snmp_351_Branch2Current stored as 0.01A."
		::= { upsApm160snmpEntry 351 }
upsApm160snmp_352_Branch2Energy OBJECT-TYPE
		SYNTAX Integer32
		
		MAX-ACCESS read-only
		STATUS current
		DESCRIPTION
		"upsApm160snmp_352_Branch2Energy stored as 0.01kWh."
		::= { upsApm160snmpEntry 352 }
upsApm160snmp_353_Branch2SwitchStatus OBJECT-TYPE
		SYNTAX INTEGER {
			open(0),
			close(1) }
		MAX-ACCESS read-only
		STATUS current
		DESCRIPTION
		"upsApm160snmp_353_Branch2SwitchStatus status."
		::= { upsApm160snmpEntry 353 }
upsApm160snmp_354_Branch2ActivePower OBJECT-TYPE
		SYNTAX Integer32
		
		MAX-ACCESS read-only
		STATUS current
		DESCRIPTION
		"upsApm160snmp_354_Branch2ActivePower stored as 0.01kW."
		::= { upsApm160snmpEntry 354 }
upsApm160snmp_355_Branch2ApparentPower OBJECT-TYPE
		SYNTAX Integer32
		
		MAX-ACCESS read-only
		STATUS current
		DESCRIPTION
		"upsApm160snmp_355_Branch2ApparentPower stored as 0.01kVA."
		::= { upsApm160snmpEntry 355 }
upsApm160snmp_356_Branch2THDi OBJECT-TYPE
		SYNTAX Integer32
		
		MAX-ACCESS read-only
		STATUS current
		DESCRIPTION
		"upsApm160snmp_356_Branch2THDi stored as 0.01%."
		::= { upsApm160snmpEntry 356 }
upsApm160snmp_357_Branch2RatedCurrent OBJECT-TYPE
		SYNTAX Integer32
		
		MAX-ACCESS read-only
		STATUS current
		DESCRIPTION
		"upsApm160snmp_357_Branch2RatedCurrent stored as 0.01A."
		::= { upsApm160snmpEntry 357 }
upsApm160snmp_358_Branch2LoadRatio OBJECT-TYPE
		SYNTAX Integer32
		
		MAX-ACCESS read-only
		STATUS current
		DESCRIPTION
		"upsApm160snmp_358_Branch2LoadRatio stored as 0.01%."
		::= { upsApm160snmpEntry 358 }
upsApm160snmp_359_Branch2PowerFactor OBJECT-TYPE
		SYNTAX Integer32
		
		MAX-ACCESS read-only
		STATUS current
		DESCRIPTION
		"upsApm160snmp_359_Branch2PowerFactor stored as 0.01."
		::= { upsApm160snmpEntry 359 }
upsApm160snmp_360_Branch2Voltage OBJECT-TYPE
		SYNTAX Integer32
		
		MAX-ACCESS read-only
		STATUS current
		DESCRIPTION
		"upsApm160snmp_360_Branch2Voltage stored as 0.01V."
		::= { upsApm160snmpEntry 360 }
upsApm160snmp_361_Branch3Current OBJECT-TYPE
		SYNTAX Integer32
		
		MAX-ACCESS read-only
		STATUS current
		DESCRIPTION
		"upsApm160snmp_361_Branch3Current stored as 0.01A."
		::= { upsApm160snmpEntry 361 }
upsApm160snmp_362_Branch3Energy OBJECT-TYPE
		SYNTAX Integer32
		
		MAX-ACCESS read-only
		STATUS current
		DESCRIPTION
		"upsApm160snmp_362_Branch3Energy stored as 0.01kWh."
		::= { upsApm160snmpEntry 362 }
upsApm160snmp_363_Branch3SwitchStatus OBJECT-TYPE
		SYNTAX INTEGER {
			open(0),
			close(1) }
		MAX-ACCESS read-only
		STATUS current
		DESCRIPTION
		"upsApm160snmp_363_Branch3SwitchStatus status."
		::= { upsApm160snmpEntry 363 }
upsApm160snmp_364_Branch3ActivePower OBJECT-TYPE
		SYNTAX Integer32
		
		MAX-ACCESS read-only
		STATUS current
		DESCRIPTION
		"upsApm160snmp_364_Branch3ActivePower stored as 0.01kW."
		::= { upsApm160snmpEntry 364 }
upsApm160snmp_365_Branch3ApparentPower OBJECT-TYPE
		SYNTAX Integer32
		
		MAX-ACCESS read-only
		STATUS current
		DESCRIPTION
		"upsApm160snmp_365_Branch3ApparentPower stored as 0.01kVA."
		::= { upsApm160snmpEntry 365 }
upsApm160snmp_366_Branch3THDi OBJECT-TYPE
		SYNTAX Integer32
		
		MAX-ACCESS read-only
		STATUS current
		DESCRIPTION
		"upsApm160snmp_366_Branch3THDi stored as 0.01%."
		::= { upsApm160snmpEntry 366 }
upsApm160snmp_367_Branch3RatedCurrent OBJECT-TYPE
		SYNTAX Integer32
		
		MAX-ACCESS read-only
		STATUS current
		DESCRIPTION
		"upsApm160snmp_367_Branch3RatedCurrent stored as 0.01A."
		::= { upsApm160snmpEntry 367 }
upsApm160snmp_368_Branch3LoadRatio OBJECT-TYPE
		SYNTAX Integer32
		
		MAX-ACCESS read-only
		STATUS current
		DESCRIPTION
		"upsApm160snmp_368_Branch3LoadRatio stored as 0.01%."
		::= { upsApm160snmpEntry 368 }
upsApm160snmp_369_Branch3PowerFactor OBJECT-TYPE
		SYNTAX Integer32
		
		MAX-ACCESS read-only
		STATUS current
		DESCRIPTION
		"upsApm160snmp_369_Branch3PowerFactor stored as 0.01."
		::= { upsApm160snmpEntry 369 }
upsApm160snmp_370_Branch3Voltage OBJECT-TYPE
		SYNTAX Integer32
		
		MAX-ACCESS read-only
		STATUS current
		DESCRIPTION
		"upsApm160snmp_370_Branch3Voltage stored as 0.01V."
		::= { upsApm160snmpEntry 370 }
upsApm160snmp_371_Branch4Current OBJECT-TYPE
		SYNTAX Integer32
		
		MAX-ACCESS read-only
		STATUS current
		DESCRIPTION
		"upsApm160snmp_371_Branch4Current stored as 0.01A."
		::= { upsApm160snmpEntry 371 }
upsApm160snmp_372_Branch4Energy OBJECT-TYPE
		SYNTAX Integer32
		
		MAX-ACCESS read-only
		STATUS current
		DESCRIPTION
		"upsApm160snmp_372_Branch4Energy stored as 0.01kWh."
		::= { upsApm160snmpEntry 372 }
upsApm160snmp_373_Branch4SwitchStatus OBJECT-TYPE
		SYNTAX INTEGER {
			open(0),
			close(1) }
		MAX-ACCESS read-only
		STATUS current
		DESCRIPTION
		"upsApm160snmp_373_Branch4SwitchStatus status."
		::= { upsApm160snmpEntry 373 }
upsApm160snmp_374_Branch4ActivePower OBJECT-TYPE
		SYNTAX Integer32
		
		MAX-ACCESS read-only
		STATUS current
		DESCRIPTION
		"upsApm160snmp_374_Branch4ActivePower stored as 0.01kW."
		::= { upsApm160snmpEntry 374 }
upsApm160snmp_375_Branch4ApparentPower OBJECT-TYPE
		SYNTAX Integer32
		
		MAX-ACCESS read-only
		STATUS current
		DESCRIPTION
		"upsApm160snmp_375_Branch4ApparentPower stored as 0.01kVA."
		::= { upsApm160snmpEntry 375 }
upsApm160snmp_376_Branch4THDi OBJECT-TYPE
		SYNTAX Integer32
		
		MAX-ACCESS read-only
		STATUS current
		DESCRIPTION
		"upsApm160snmp_376_Branch4THDi stored as 0.01%."
		::= { upsApm160snmpEntry 376 }
upsApm160snmp_377_Branch4RatedCurrent OBJECT-TYPE
		SYNTAX Integer32
		
		MAX-ACCESS read-only
		STATUS current
		DESCRIPTION
		"upsApm160snmp_377_Branch4RatedCurrent stored as 0.01A."
		::= { upsApm160snmpEntry 377 }
upsApm160snmp_378_Branch4LoadRatio OBJECT-TYPE
		SYNTAX Integer32
		
		MAX-ACCESS read-only
		STATUS current
		DESCRIPTION
		"upsApm160snmp_378_Branch4LoadRatio stored as 0.01%."
		::= { upsApm160snmpEntry 378 }
upsApm160snmp_379_Branch4PowerFactor OBJECT-TYPE
		SYNTAX Integer32
		
		MAX-ACCESS read-only
		STATUS current
		DESCRIPTION
		"upsApm160snmp_379_Branch4PowerFactor stored as 0.01."
		::= { upsApm160snmpEntry 379 }
upsApm160snmp_380_Branch4Voltage OBJECT-TYPE
		SYNTAX Integer32
		
		MAX-ACCESS read-only
		STATUS current
		DESCRIPTION
		"upsApm160snmp_380_Branch4Voltage stored as 0.01V."
		::= { upsApm160snmpEntry 380 }
upsApm160snmp_381_Branch5Current OBJECT-TYPE
		SYNTAX Integer32
		
		MAX-ACCESS read-only
		STATUS current
		DESCRIPTION
		"upsApm160snmp_381_Branch5Current stored as 0.01A."
		::= { upsApm160snmpEntry 381 }
upsApm160snmp_382_Branch5Energy OBJECT-TYPE
		SYNTAX Integer32
		
		MAX-ACCESS read-only
		STATUS current
		DESCRIPTION
		"upsApm160snmp_382_Branch5Energy stored as 0.01kWh."
		::= { upsApm160snmpEntry 382 }
upsApm160snmp_383_Branch5SwitchStatus OBJECT-TYPE
		SYNTAX INTEGER {
			open(0),
			close(1) }
		MAX-ACCESS read-only
		STATUS current
		DESCRIPTION
		"upsApm160snmp_383_Branch5SwitchStatus status."
		::= { upsApm160snmpEntry 383 }
upsApm160snmp_384_Branch5ActivePower OBJECT-TYPE
		SYNTAX Integer32
		
		MAX-ACCESS read-only
		STATUS current
		DESCRIPTION
		"upsApm160snmp_384_Branch5ActivePower stored as 0.01kW."
		::= { upsApm160snmpEntry 384 }
upsApm160snmp_385_Branch5ApparentPower OBJECT-TYPE
		SYNTAX Integer32
		
		MAX-ACCESS read-only
		STATUS current
		DESCRIPTION
		"upsApm160snmp_385_Branch5ApparentPower stored as 0.01kVA."
		::= { upsApm160snmpEntry 385 }
upsApm160snmp_386_Branch5THDi OBJECT-TYPE
		SYNTAX Integer32
		
		MAX-ACCESS read-only
		STATUS current
		DESCRIPTION
		"upsApm160snmp_386_Branch5THDi stored as 0.01%."
		::= { upsApm160snmpEntry 386 }
upsApm160snmp_387_Branch5RatedCurrent OBJECT-TYPE
		SYNTAX Integer32
		
		MAX-ACCESS read-only
		STATUS current
		DESCRIPTION
		"upsApm160snmp_387_Branch5RatedCurrent stored as 0.01A."
		::= { upsApm160snmpEntry 387 }
upsApm160snmp_388_Branch5LoadRatio OBJECT-TYPE
		SYNTAX Integer32
		
		MAX-ACCESS read-only
		STATUS current
		DESCRIPTION
		"upsApm160snmp_388_Branch5LoadRatio stored as 0.01%."
		::= { upsApm160snmpEntry 388 }
upsApm160snmp_389_Branch5PowerFactor OBJECT-TYPE
		SYNTAX Integer32
		
		MAX-ACCESS read-only
		STATUS current
		DESCRIPTION
		"upsApm160snmp_389_Branch5PowerFactor stored as 0.01."
		::= { upsApm160snmpEntry 389 }
upsApm160snmp_390_Branch5Voltage OBJECT-TYPE
		SYNTAX Integer32
		
		MAX-ACCESS read-only
		STATUS current
		DESCRIPTION
		"upsApm160snmp_390_Branch5Voltage stored as 0.01V."
		::= { upsApm160snmpEntry 390 }
upsApm160snmp_391_Branch6Current OBJECT-TYPE
		SYNTAX Integer32
		
		MAX-ACCESS read-only
		STATUS current
		DESCRIPTION
		"upsApm160snmp_391_Branch6Current stored as 0.01A."
		::= { upsApm160snmpEntry 391 }
upsApm160snmp_392_Branch6Energy OBJECT-TYPE
		SYNTAX Integer32
		
		MAX-ACCESS read-only
		STATUS current
		DESCRIPTION
		"upsApm160snmp_392_Branch6Energy stored as 0.01kWh."
		::= { upsApm160snmpEntry 392 }
upsApm160snmp_393_Branch6SwitchStatus OBJECT-TYPE
		SYNTAX INTEGER {
			open(0),
			close(1) }
		MAX-ACCESS read-only
		STATUS current
		DESCRIPTION
		"upsApm160snmp_393_Branch6SwitchStatus status."
		::= { upsApm160snmpEntry 393 }
upsApm160snmp_394_Branch6ActivePower OBJECT-TYPE
		SYNTAX Integer32
		
		MAX-ACCESS read-only
		STATUS current
		DESCRIPTION
		"upsApm160snmp_394_Branch6ActivePower stored as 0.01kW."
		::= { upsApm160snmpEntry 394 }
upsApm160snmp_395_Branch6ApparentPower OBJECT-TYPE
		SYNTAX Integer32
		
		MAX-ACCESS read-only
		STATUS current
		DESCRIPTION
		"upsApm160snmp_395_Branch6ApparentPower stored as 0.01kVA."
		::= { upsApm160snmpEntry 395 }
upsApm160snmp_396_Branch6THDi OBJECT-TYPE
		SYNTAX Integer32
		
		MAX-ACCESS read-only
		STATUS current
		DESCRIPTION
		"upsApm160snmp_396_Branch6THDi stored as 0.01%."
		::= { upsApm160snmpEntry 396 }
upsApm160snmp_397_Branch6RatedCurrent OBJECT-TYPE
		SYNTAX Integer32
		
		MAX-ACCESS read-only
		STATUS current
		DESCRIPTION
		"upsApm160snmp_397_Branch6RatedCurrent stored as 0.01A."
		::= { upsApm160snmpEntry 397 }
upsApm160snmp_398_Branch6LoadRatio OBJECT-TYPE
		SYNTAX Integer32
		
		MAX-ACCESS read-only
		STATUS current
		DESCRIPTION
		"upsApm160snmp_398_Branch6LoadRatio stored as 0.01%."
		::= { upsApm160snmpEntry 398 }
upsApm160snmp_399_Branch6PowerFactor OBJECT-TYPE
		SYNTAX Integer32
		
		MAX-ACCESS read-only
		STATUS current
		DESCRIPTION
		"upsApm160snmp_399_Branch6PowerFactor stored as 0.01."
		::= { upsApm160snmpEntry 399 }
upsApm160snmp_400_Branch6Voltage OBJECT-TYPE
		SYNTAX Integer32
		
		MAX-ACCESS read-only
		STATUS current
		DESCRIPTION
		"upsApm160snmp_400_Branch6Voltage stored as 0.01V."
		::= { upsApm160snmpEntry 400 }
upsApm160snmp_401_Branch7Current OBJECT-TYPE
		SYNTAX Integer32
		
		MAX-ACCESS read-only
		STATUS current
		DESCRIPTION
		"upsApm160snmp_401_Branch7Current stored as 0.01A."
		::= { upsApm160snmpEntry 401 }
upsApm160snmp_402_Branch7Energy OBJECT-TYPE
		SYNTAX Integer32
		
		MAX-ACCESS read-only
		STATUS current
		DESCRIPTION
		"upsApm160snmp_402_Branch7Energy stored as 0.01kWh."
		::= { upsApm160snmpEntry 402 }
upsApm160snmp_403_Branch7SwitchStatus OBJECT-TYPE
		SYNTAX INTEGER {
			open(0),
			close(1) }
		MAX-ACCESS read-only
		STATUS current
		DESCRIPTION
		"upsApm160snmp_403_Branch7SwitchStatus status."
		::= { upsApm160snmpEntry 403 }
upsApm160snmp_404_Branch7ActivePower OBJECT-TYPE
		SYNTAX Integer32
		
		MAX-ACCESS read-only
		STATUS current
		DESCRIPTION
		"upsApm160snmp_404_Branch7ActivePower stored as 0.01kW."
		::= { upsApm160snmpEntry 404 }
upsApm160snmp_405_Branch7ApparentPower OBJECT-TYPE
		SYNTAX Integer32
		
		MAX-ACCESS read-only
		STATUS current
		DESCRIPTION
		"upsApm160snmp_405_Branch7ApparentPower stored as 0.01kVA."
		::= { upsApm160snmpEntry 405 }
upsApm160snmp_406_Branch7THDi OBJECT-TYPE
		SYNTAX Integer32
		
		MAX-ACCESS read-only
		STATUS current
		DESCRIPTION
		"upsApm160snmp_406_Branch7THDi stored as 0.01%."
		::= { upsApm160snmpEntry 406 }
upsApm160snmp_407_Branch7RatedCurrent OBJECT-TYPE
		SYNTAX Integer32
		
		MAX-ACCESS read-only
		STATUS current
		DESCRIPTION
		"upsApm160snmp_407_Branch7RatedCurrent stored as 0.01A."
		::= { upsApm160snmpEntry 407 }
upsApm160snmp_408_Branch7LoadRatio OBJECT-TYPE
		SYNTAX Integer32
		
		MAX-ACCESS read-only
		STATUS current
		DESCRIPTION
		"upsApm160snmp_408_Branch7LoadRatio stored as 0.01%."
		::= { upsApm160snmpEntry 408 }
upsApm160snmp_409_Branch7PowerFactor OBJECT-TYPE
		SYNTAX Integer32
		
		MAX-ACCESS read-only
		STATUS current
		DESCRIPTION
		"upsApm160snmp_409_Branch7PowerFactor stored as 0.01."
		::= { upsApm160snmpEntry 409 }
upsApm160snmp_410_Branch7Voltage OBJECT-TYPE
		SYNTAX Integer32
		
		MAX-ACCESS read-only
		STATUS current
		DESCRIPTION
		"upsApm160snmp_410_Branch7Voltage stored as 0.01V."
		::= { upsApm160snmpEntry 410 }
upsApm160snmp_411_Branch8Current OBJECT-TYPE
		SYNTAX Integer32
		
		MAX-ACCESS read-only
		STATUS current
		DESCRIPTION
		"upsApm160snmp_411_Branch8Current stored as 0.01A."
		::= { upsApm160snmpEntry 411 }
upsApm160snmp_412_Branch8Energy OBJECT-TYPE
		SYNTAX Integer32
		
		MAX-ACCESS read-only
		STATUS current
		DESCRIPTION
		"upsApm160snmp_412_Branch8Energy stored as 0.01kWh."
		::= { upsApm160snmpEntry 412 }
upsApm160snmp_413_Branch8SwitchStatus OBJECT-TYPE
		SYNTAX INTEGER {
			open(0),
			close(1) }
		MAX-ACCESS read-only
		STATUS current
		DESCRIPTION
		"upsApm160snmp_413_Branch8SwitchStatus status."
		::= { upsApm160snmpEntry 413 }
upsApm160snmp_414_Branch8ActivePower OBJECT-TYPE
		SYNTAX Integer32
		
		MAX-ACCESS read-only
		STATUS current
		DESCRIPTION
		"upsApm160snmp_414_Branch8ActivePower stored as 0.01kW."
		::= { upsApm160snmpEntry 414 }
upsApm160snmp_415_Branch8ApparentPower OBJECT-TYPE
		SYNTAX Integer32
		
		MAX-ACCESS read-only
		STATUS current
		DESCRIPTION
		"upsApm160snmp_415_Branch8ApparentPower stored as 0.01kVA."
		::= { upsApm160snmpEntry 415 }
upsApm160snmp_416_Branch8THDi OBJECT-TYPE
		SYNTAX Integer32
		
		MAX-ACCESS read-only
		STATUS current
		DESCRIPTION
		"upsApm160snmp_416_Branch8THDi stored as 0.01%."
		::= { upsApm160snmpEntry 416 }
upsApm160snmp_417_Branch8RatedCurrent OBJECT-TYPE
		SYNTAX Integer32
		
		MAX-ACCESS read-only
		STATUS current
		DESCRIPTION
		"upsApm160snmp_417_Branch8RatedCurrent stored as 0.01A."
		::= { upsApm160snmpEntry 417 }
upsApm160snmp_418_Branch8LoadRatio OBJECT-TYPE
		SYNTAX Integer32
		
		MAX-ACCESS read-only
		STATUS current
		DESCRIPTION
		"upsApm160snmp_418_Branch8LoadRatio stored as 0.01%."
		::= { upsApm160snmpEntry 418 }
upsApm160snmp_419_Branch8PowerFactor OBJECT-TYPE
		SYNTAX Integer32
		
		MAX-ACCESS read-only
		STATUS current
		DESCRIPTION
		"upsApm160snmp_419_Branch8PowerFactor stored as 0.01."
		::= { upsApm160snmpEntry 419 }
upsApm160snmp_420_Branch8Voltage OBJECT-TYPE
		SYNTAX Integer32
		
		MAX-ACCESS read-only
		STATUS current
		DESCRIPTION
		"upsApm160snmp_420_Branch8Voltage stored as 0.01V."
		::= { upsApm160snmpEntry 420 }
upsApm160snmp_421_Branch9Current OBJECT-TYPE
		SYNTAX Integer32
		
		MAX-ACCESS read-only
		STATUS current
		DESCRIPTION
		"upsApm160snmp_421_Branch9Current stored as 0.01A."
		::= { upsApm160snmpEntry 421 }
upsApm160snmp_422_Branch9Energy OBJECT-TYPE
		SYNTAX Integer32
		
		MAX-ACCESS read-only
		STATUS current
		DESCRIPTION
		"upsApm160snmp_422_Branch9Energy stored as 0.01kWh."
		::= { upsApm160snmpEntry 422 }
upsApm160snmp_423_Branch9SwitchStatus OBJECT-TYPE
		SYNTAX INTEGER {
			open(0),
			close(1) }
		MAX-ACCESS read-only
		STATUS current
		DESCRIPTION
		"upsApm160snmp_423_Branch9SwitchStatus status."
		::= { upsApm160snmpEntry 423 }
upsApm160snmp_424_Branch9ActivePower OBJECT-TYPE
		SYNTAX Integer32
		
		MAX-ACCESS read-only
		STATUS current
		DESCRIPTION
		"upsApm160snmp_424_Branch9ActivePower stored as 0.01kW."
		::= { upsApm160snmpEntry 424 }
upsApm160snmp_425_Branch9ApparentPower OBJECT-TYPE
		SYNTAX Integer32
		
		MAX-ACCESS read-only
		STATUS current
		DESCRIPTION
		"upsApm160snmp_425_Branch9ApparentPower stored as 0.01kVA."
		::= { upsApm160snmpEntry 425 }
upsApm160snmp_426_Branch9THDi OBJECT-TYPE
		SYNTAX Integer32
		
		MAX-ACCESS read-only
		STATUS current
		DESCRIPTION
		"upsApm160snmp_426_Branch9THDi stored as 0.01%."
		::= { upsApm160snmpEntry 426 }
upsApm160snmp_427_Branch9RatedCurrent OBJECT-TYPE
		SYNTAX Integer32
		
		MAX-ACCESS read-only
		STATUS current
		DESCRIPTION
		"upsApm160snmp_427_Branch9RatedCurrent stored as 0.01A."
		::= { upsApm160snmpEntry 427 }
upsApm160snmp_428_Branch9LoadRatio OBJECT-TYPE
		SYNTAX Integer32
		
		MAX-ACCESS read-only
		STATUS current
		DESCRIPTION
		"upsApm160snmp_428_Branch9LoadRatio stored as 0.01%."
		::= { upsApm160snmpEntry 428 }
upsApm160snmp_429_Branch9PowerFactor OBJECT-TYPE
		SYNTAX Integer32
		
		MAX-ACCESS read-only
		STATUS current
		DESCRIPTION
		"upsApm160snmp_429_Branch9PowerFactor stored as 0.01."
		::= { upsApm160snmpEntry 429 }
upsApm160snmp_430_Branch9Voltage OBJECT-TYPE
		SYNTAX Integer32
		
		MAX-ACCESS read-only
		STATUS current
		DESCRIPTION
		"upsApm160snmp_430_Branch9Voltage stored as 0.01V."
		::= { upsApm160snmpEntry 430 }
upsApm160snmp_431_Branch10Current OBJECT-TYPE
		SYNTAX Integer32
		
		MAX-ACCESS read-only
		STATUS current
		DESCRIPTION
		"upsApm160snmp_431_Branch10Current stored as 0.01A."
		::= { upsApm160snmpEntry 431 }
upsApm160snmp_432_Branch10Energy OBJECT-TYPE
		SYNTAX Integer32
		
		MAX-ACCESS read-only
		STATUS current
		DESCRIPTION
		"upsApm160snmp_432_Branch10Energy stored as 0.01kWh."
		::= { upsApm160snmpEntry 432 }
upsApm160snmp_433_Branch10SwitchStatus OBJECT-TYPE
		SYNTAX INTEGER {
			open(0),
			close(1) }
		MAX-ACCESS read-only
		STATUS current
		DESCRIPTION
		"upsApm160snmp_433_Branch10SwitchStatus status."
		::= { upsApm160snmpEntry 433 }
upsApm160snmp_434_Branch10ActivePower OBJECT-TYPE
		SYNTAX Integer32
		
		MAX-ACCESS read-only
		STATUS current
		DESCRIPTION
		"upsApm160snmp_434_Branch10ActivePower stored as 0.01kW."
		::= { upsApm160snmpEntry 434 }
upsApm160snmp_435_Branch10ApparentPower OBJECT-TYPE
		SYNTAX Integer32
		
		MAX-ACCESS read-only
		STATUS current
		DESCRIPTION
		"upsApm160snmp_435_Branch10ApparentPower stored as 0.01kVA."
		::= { upsApm160snmpEntry 435 }
upsApm160snmp_436_Branch10THDi OBJECT-TYPE
		SYNTAX Integer32
		
		MAX-ACCESS read-only
		STATUS current
		DESCRIPTION
		"upsApm160snmp_436_Branch10THDi stored as 0.01%."
		::= { upsApm160snmpEntry 436 }
upsApm160snmp_437_Branch10RatedCurrent OBJECT-TYPE
		SYNTAX Integer32
		
		MAX-ACCESS read-only
		STATUS current
		DESCRIPTION
		"upsApm160snmp_437_Branch10RatedCurrent stored as 0.01A."
		::= { upsApm160snmpEntry 437 }
upsApm160snmp_438_Branch10LoadRatio OBJECT-TYPE
		SYNTAX Integer32
		
		MAX-ACCESS read-only
		STATUS current
		DESCRIPTION
		"upsApm160snmp_438_Branch10LoadRatio stored as 0.01%."
		::= { upsApm160snmpEntry 438 }
upsApm160snmp_439_Branch10PowerFactor OBJECT-TYPE
		SYNTAX Integer32
		
		MAX-ACCESS read-only
		STATUS current
		DESCRIPTION
		"upsApm160snmp_439_Branch10PowerFactor stored as 0.01."
		::= { upsApm160snmpEntry 439 }
upsApm160snmp_440_Branch10Voltage OBJECT-TYPE
		SYNTAX Integer32
		
		MAX-ACCESS read-only
		STATUS current
		DESCRIPTION
		"upsApm160snmp_440_Branch10Voltage stored as 0.01V."
		::= { upsApm160snmpEntry 440 }
upsApm160snmp_441_Branch11Current OBJECT-TYPE
		SYNTAX Integer32
		
		MAX-ACCESS read-only
		STATUS current
		DESCRIPTION
		"upsApm160snmp_441_Branch11Current stored as 0.01A."
		::= { upsApm160snmpEntry 441 }
upsApm160snmp_442_Branch11Energy OBJECT-TYPE
		SYNTAX Integer32
		
		MAX-ACCESS read-only
		STATUS current
		DESCRIPTION
		"upsApm160snmp_442_Branch11Energy stored as 0.01kWh."
		::= { upsApm160snmpEntry 442 }
upsApm160snmp_443_Branch11SwitchStatus OBJECT-TYPE
		SYNTAX INTEGER {
			open(0),
			close(1) }
		MAX-ACCESS read-only
		STATUS current
		DESCRIPTION
		"upsApm160snmp_443_Branch11SwitchStatus status."
		::= { upsApm160snmpEntry 443 }
upsApm160snmp_444_Branch11ActivePower OBJECT-TYPE
		SYNTAX Integer32
		
		MAX-ACCESS read-only
		STATUS current
		DESCRIPTION
		"upsApm160snmp_444_Branch11ActivePower stored as 0.01kW."
		::= { upsApm160snmpEntry 444 }
upsApm160snmp_445_Branch11ApparentPower OBJECT-TYPE
		SYNTAX Integer32
		
		MAX-ACCESS read-only
		STATUS current
		DESCRIPTION
		"upsApm160snmp_445_Branch11ApparentPower stored as 0.01kVA."
		::= { upsApm160snmpEntry 445 }
upsApm160snmp_446_Branch11THDi OBJECT-TYPE
		SYNTAX Integer32
		
		MAX-ACCESS read-only
		STATUS current
		DESCRIPTION
		"upsApm160snmp_446_Branch11THDi stored as 0.01%."
		::= { upsApm160snmpEntry 446 }
upsApm160snmp_447_Branch11RatedCurrent OBJECT-TYPE
		SYNTAX Integer32
		
		MAX-ACCESS read-only
		STATUS current
		DESCRIPTION
		"upsApm160snmp_447_Branch11RatedCurrent stored as 0.01A."
		::= { upsApm160snmpEntry 447 }
upsApm160snmp_448_Branch11LoadRatio OBJECT-TYPE
		SYNTAX Integer32
		
		MAX-ACCESS read-only
		STATUS current
		DESCRIPTION
		"upsApm160snmp_448_Branch11LoadRatio stored as 0.01%."
		::= { upsApm160snmpEntry 448 }
upsApm160snmp_449_Branch11PowerFactor OBJECT-TYPE
		SYNTAX Integer32
		
		MAX-ACCESS read-only
		STATUS current
		DESCRIPTION
		"upsApm160snmp_449_Branch11PowerFactor stored as 0.01."
		::= { upsApm160snmpEntry 449 }
upsApm160snmp_450_Branch11Voltage OBJECT-TYPE
		SYNTAX Integer32
		
		MAX-ACCESS read-only
		STATUS current
		DESCRIPTION
		"upsApm160snmp_450_Branch11Voltage stored as 0.01V."
		::= { upsApm160snmpEntry 450 }
upsApm160snmp_451_Branch12Current OBJECT-TYPE
		SYNTAX Integer32
		
		MAX-ACCESS read-only
		STATUS current
		DESCRIPTION
		"upsApm160snmp_451_Branch12Current stored as 0.01A."
		::= { upsApm160snmpEntry 451 }
upsApm160snmp_452_Branch12Energy OBJECT-TYPE
		SYNTAX Integer32
		
		MAX-ACCESS read-only
		STATUS current
		DESCRIPTION
		"upsApm160snmp_452_Branch12Energy stored as 0.01kWh."
		::= { upsApm160snmpEntry 452 }
upsApm160snmp_453_Branch12SwitchStatus OBJECT-TYPE
		SYNTAX INTEGER {
			open(0),
			close(1) }
		MAX-ACCESS read-only
		STATUS current
		DESCRIPTION
		"upsApm160snmp_453_Branch12SwitchStatus status."
		::= { upsApm160snmpEntry 453 }
upsApm160snmp_454_Branch12ActivePower OBJECT-TYPE
		SYNTAX Integer32
		
		MAX-ACCESS read-only
		STATUS current
		DESCRIPTION
		"upsApm160snmp_454_Branch12ActivePower stored as 0.01kW."
		::= { upsApm160snmpEntry 454 }
upsApm160snmp_455_Branch12ApparentPower OBJECT-TYPE
		SYNTAX Integer32
		
		MAX-ACCESS read-only
		STATUS current
		DESCRIPTION
		"upsApm160snmp_455_Branch12ApparentPower stored as 0.01kVA."
		::= { upsApm160snmpEntry 455 }
upsApm160snmp_456_Branch12THDi OBJECT-TYPE
		SYNTAX Integer32
		
		MAX-ACCESS read-only
		STATUS current
		DESCRIPTION
		"upsApm160snmp_456_Branch12THDi stored as 0.01%."
		::= { upsApm160snmpEntry 456 }
upsApm160snmp_457_Branch12RatedCurrent OBJECT-TYPE
		SYNTAX Integer32
		
		MAX-ACCESS read-only
		STATUS current
		DESCRIPTION
		"upsApm160snmp_457_Branch12RatedCurrent stored as 0.01A."
		::= { upsApm160snmpEntry 457 }
upsApm160snmp_458_Branch12LoadRatio OBJECT-TYPE
		SYNTAX Integer32
		
		MAX-ACCESS read-only
		STATUS current
		DESCRIPTION
		"upsApm160snmp_458_Branch12LoadRatio stored as 0.01%."
		::= { upsApm160snmpEntry 458 }
upsApm160snmp_459_Branch12PowerFactor OBJECT-TYPE
		SYNTAX Integer32
		
		MAX-ACCESS read-only
		STATUS current
		DESCRIPTION
		"upsApm160snmp_459_Branch12PowerFactor stored as 0.01."
		::= { upsApm160snmpEntry 459 }
upsApm160snmp_460_Branch12Voltage OBJECT-TYPE
		SYNTAX Integer32
		
		MAX-ACCESS read-only
		STATUS current
		DESCRIPTION
		"upsApm160snmp_460_Branch12Voltage stored as 0.01V."
		::= { upsApm160snmpEntry 460 }
upsApm160snmp_461_Branch13Current OBJECT-TYPE
		SYNTAX Integer32
		
		MAX-ACCESS read-only
		STATUS current
		DESCRIPTION
		"upsApm160snmp_461_Branch13Current stored as 0.01A."
		::= { upsApm160snmpEntry 461 }
upsApm160snmp_462_Branch13Energy OBJECT-TYPE
		SYNTAX Integer32
		
		MAX-ACCESS read-only
		STATUS current
		DESCRIPTION
		"upsApm160snmp_462_Branch13Energy stored as 0.01kWh."
		::= { upsApm160snmpEntry 462 }
upsApm160snmp_463_Branch13SwitchStatus OBJECT-TYPE
		SYNTAX INTEGER {
			open(0),
			close(1) }
		MAX-ACCESS read-only
		STATUS current
		DESCRIPTION
		"upsApm160snmp_463_Branch13SwitchStatus status."
		::= { upsApm160snmpEntry 463 }
upsApm160snmp_464_Branch13ActivePower OBJECT-TYPE
		SYNTAX Integer32
		
		MAX-ACCESS read-only
		STATUS current
		DESCRIPTION
		"upsApm160snmp_464_Branch13ActivePower stored as 0.01kW."
		::= { upsApm160snmpEntry 464 }
upsApm160snmp_465_Branch13ApparentPower OBJECT-TYPE
		SYNTAX Integer32
		
		MAX-ACCESS read-only
		STATUS current
		DESCRIPTION
		"upsApm160snmp_465_Branch13ApparentPower stored as 0.01kVA."
		::= { upsApm160snmpEntry 465 }
upsApm160snmp_466_Branch13THDi OBJECT-TYPE
		SYNTAX Integer32
		
		MAX-ACCESS read-only
		STATUS current
		DESCRIPTION
		"upsApm160snmp_466_Branch13THDi stored as 0.01%."
		::= { upsApm160snmpEntry 466 }
upsApm160snmp_467_Branch13RatedCurrent OBJECT-TYPE
		SYNTAX Integer32
		
		MAX-ACCESS read-only
		STATUS current
		DESCRIPTION
		"upsApm160snmp_467_Branch13RatedCurrent stored as 0.01A."
		::= { upsApm160snmpEntry 467 }
upsApm160snmp_468_Branch13LoadRatio OBJECT-TYPE
		SYNTAX Integer32
		
		MAX-ACCESS read-only
		STATUS current
		DESCRIPTION
		"upsApm160snmp_468_Branch13LoadRatio stored as 0.01%."
		::= { upsApm160snmpEntry 468 }
upsApm160snmp_469_Branch13PowerFactor OBJECT-TYPE
		SYNTAX Integer32
		
		MAX-ACCESS read-only
		STATUS current
		DESCRIPTION
		"upsApm160snmp_469_Branch13PowerFactor stored as 0.01."
		::= { upsApm160snmpEntry 469 }
upsApm160snmp_470_Branch13Voltage OBJECT-TYPE
		SYNTAX Integer32
		
		MAX-ACCESS read-only
		STATUS current
		DESCRIPTION
		"upsApm160snmp_470_Branch13Voltage stored as 0.01V."
		::= { upsApm160snmpEntry 470 }
upsApm160snmp_471_Branch14Current OBJECT-TYPE
		SYNTAX Integer32
		
		MAX-ACCESS read-only
		STATUS current
		DESCRIPTION
		"upsApm160snmp_471_Branch14Current stored as 0.01A."
		::= { upsApm160snmpEntry 471 }
upsApm160snmp_472_Branch14Energy OBJECT-TYPE
		SYNTAX Integer32
		
		MAX-ACCESS read-only
		STATUS current
		DESCRIPTION
		"upsApm160snmp_472_Branch14Energy stored as 0.01kWh."
		::= { upsApm160snmpEntry 472 }
upsApm160snmp_473_Branch14SwitchStatus OBJECT-TYPE
		SYNTAX INTEGER {
			open(0),
			close(1) }
		MAX-ACCESS read-only
		STATUS current
		DESCRIPTION
		"upsApm160snmp_473_Branch14SwitchStatus status."
		::= { upsApm160snmpEntry 473 }
upsApm160snmp_474_Branch14ActivePower OBJECT-TYPE
		SYNTAX Integer32
		
		MAX-ACCESS read-only
		STATUS current
		DESCRIPTION
		"upsApm160snmp_474_Branch14ActivePower stored as 0.01kW."
		::= { upsApm160snmpEntry 474 }
upsApm160snmp_475_Branch14ApparentPower OBJECT-TYPE
		SYNTAX Integer32
		
		MAX-ACCESS read-only
		STATUS current
		DESCRIPTION
		"upsApm160snmp_475_Branch14ApparentPower stored as 0.01kVA."
		::= { upsApm160snmpEntry 475 }
upsApm160snmp_476_Branch14THDi OBJECT-TYPE
		SYNTAX Integer32
		
		MAX-ACCESS read-only
		STATUS current
		DESCRIPTION
		"upsApm160snmp_476_Branch14THDi stored as 0.01%."
		::= { upsApm160snmpEntry 476 }
upsApm160snmp_477_Branch14RatedCurrent OBJECT-TYPE
		SYNTAX Integer32
		
		MAX-ACCESS read-only
		STATUS current
		DESCRIPTION
		"upsApm160snmp_477_Branch14RatedCurrent stored as 0.01A."
		::= { upsApm160snmpEntry 477 }
upsApm160snmp_478_Branch14LoadRatio OBJECT-TYPE
		SYNTAX Integer32
		
		MAX-ACCESS read-only
		STATUS current
		DESCRIPTION
		"upsApm160snmp_478_Branch14LoadRatio stored as 0.01%."
		::= { upsApm160snmpEntry 478 }
upsApm160snmp_479_Branch14PowerFactor OBJECT-TYPE
		SYNTAX Integer32
		
		MAX-ACCESS read-only
		STATUS current
		DESCRIPTION
		"upsApm160snmp_479_Branch14PowerFactor stored as 0.01."
		::= { upsApm160snmpEntry 479 }
upsApm160snmp_480_Branch14Voltage OBJECT-TYPE
		SYNTAX Integer32
		
		MAX-ACCESS read-only
		STATUS current
		DESCRIPTION
		"upsApm160snmp_480_Branch14Voltage stored as 0.01V."
		::= { upsApm160snmpEntry 480 }
upsApm160snmp_481_Branch15Current OBJECT-TYPE
		SYNTAX Integer32
		
		MAX-ACCESS read-only
		STATUS current
		DESCRIPTION
		"upsApm160snmp_481_Branch15Current stored as 0.01A."
		::= { upsApm160snmpEntry 481 }
upsApm160snmp_482_Branch15Energy OBJECT-TYPE
		SYNTAX Integer32
		
		MAX-ACCESS read-only
		STATUS current
		DESCRIPTION
		"upsApm160snmp_482_Branch15Energy stored as 0.01kWh."
		::= { upsApm160snmpEntry 482 }
upsApm160snmp_483_Branch15SwitchStatus OBJECT-TYPE
		SYNTAX INTEGER {
			open(0),
			close(1) }
		MAX-ACCESS read-only
		STATUS current
		DESCRIPTION
		"upsApm160snmp_483_Branch15SwitchStatus status."
		::= { upsApm160snmpEntry 483 }
upsApm160snmp_484_Branch15ActivePower OBJECT-TYPE
		SYNTAX Integer32
		
		MAX-ACCESS read-only
		STATUS current
		DESCRIPTION
		"upsApm160snmp_484_Branch15ActivePower stored as 0.01kW."
		::= { upsApm160snmpEntry 484 }
upsApm160snmp_485_Branch15ApparentPower OBJECT-TYPE
		SYNTAX Integer32
		
		MAX-ACCESS read-only
		STATUS current
		DESCRIPTION
		"upsApm160snmp_485_Branch15ApparentPower stored as 0.01kVA."
		::= { upsApm160snmpEntry 485 }
upsApm160snmp_486_Branch15THDi OBJECT-TYPE
		SYNTAX Integer32
		
		MAX-ACCESS read-only
		STATUS current
		DESCRIPTION
		"upsApm160snmp_486_Branch15THDi stored as 0.01%."
		::= { upsApm160snmpEntry 486 }
upsApm160snmp_487_Branch15RatedCurrent OBJECT-TYPE
		SYNTAX Integer32
		
		MAX-ACCESS read-only
		STATUS current
		DESCRIPTION
		"upsApm160snmp_487_Branch15RatedCurrent stored as 0.01A."
		::= { upsApm160snmpEntry 487 }
upsApm160snmp_488_Branch15LoadRatio OBJECT-TYPE
		SYNTAX Integer32
		
		MAX-ACCESS read-only
		STATUS current
		DESCRIPTION
		"upsApm160snmp_488_Branch15LoadRatio stored as 0.01%."
		::= { upsApm160snmpEntry 488 }
upsApm160snmp_489_Branch15PowerFactor OBJECT-TYPE
		SYNTAX Integer32
		
		MAX-ACCESS read-only
		STATUS current
		DESCRIPTION
		"upsApm160snmp_489_Branch15PowerFactor stored as 0.01."
		::= { upsApm160snmpEntry 489 }
upsApm160snmp_490_Branch15Voltage OBJECT-TYPE
		SYNTAX Integer32
		
		MAX-ACCESS read-only
		STATUS current
		DESCRIPTION
		"upsApm160snmp_490_Branch15Voltage stored as 0.01V."
		::= { upsApm160snmpEntry 490 }
upsApm160snmp_491_Branch16Current OBJECT-TYPE
		SYNTAX Integer32
		
		MAX-ACCESS read-only
		STATUS current
		DESCRIPTION
		"upsApm160snmp_491_Branch16Current stored as 0.01A."
		::= { upsApm160snmpEntry 491 }
upsApm160snmp_492_Branch16Energy OBJECT-TYPE
		SYNTAX Integer32
		
		MAX-ACCESS read-only
		STATUS current
		DESCRIPTION
		"upsApm160snmp_492_Branch16Energy stored as 0.01kWh."
		::= { upsApm160snmpEntry 492 }
upsApm160snmp_493_Branch16SwitchStatus OBJECT-TYPE
		SYNTAX INTEGER {
			open(0),
			close(1) }
		MAX-ACCESS read-only
		STATUS current
		DESCRIPTION
		"upsApm160snmp_493_Branch16SwitchStatus status."
		::= { upsApm160snmpEntry 493 }
upsApm160snmp_494_Branch16ActivePower OBJECT-TYPE
		SYNTAX Integer32
		
		MAX-ACCESS read-only
		STATUS current
		DESCRIPTION
		"upsApm160snmp_494_Branch16ActivePower stored as 0.01kW."
		::= { upsApm160snmpEntry 494 }
upsApm160snmp_495_Branch16ApparentPower OBJECT-TYPE
		SYNTAX Integer32
		
		MAX-ACCESS read-only
		STATUS current
		DESCRIPTION
		"upsApm160snmp_495_Branch16ApparentPower stored as 0.01kVA."
		::= { upsApm160snmpEntry 495 }
upsApm160snmp_496_Branch16THDi OBJECT-TYPE
		SYNTAX Integer32
		
		MAX-ACCESS read-only
		STATUS current
		DESCRIPTION
		"upsApm160snmp_496_Branch16THDi stored as 0.01%."
		::= { upsApm160snmpEntry 496 }
upsApm160snmp_497_Branch16RatedCurrent OBJECT-TYPE
		SYNTAX Integer32
		
		MAX-ACCESS read-only
		STATUS current
		DESCRIPTION
		"upsApm160snmp_497_Branch16RatedCurrent stored as 0.01A."
		::= { upsApm160snmpEntry 497 }
upsApm160snmp_498_Branch16LoadRatio OBJECT-TYPE
		SYNTAX Integer32
		
		MAX-ACCESS read-only
		STATUS current
		DESCRIPTION
		"upsApm160snmp_498_Branch16LoadRatio stored as 0.01%."
		::= { upsApm160snmpEntry 498 }
upsApm160snmp_499_Branch16PowerFactor OBJECT-TYPE
		SYNTAX Integer32
		
		MAX-ACCESS read-only
		STATUS current
		DESCRIPTION
		"upsApm160snmp_499_Branch16PowerFactor stored as 0.01."
		::= { upsApm160snmpEntry 499 }
upsApm160snmp_500_Branch16Voltage OBJECT-TYPE
		SYNTAX Integer32
		
		MAX-ACCESS read-only
		STATUS current
		DESCRIPTION
		"upsApm160snmp_500_Branch16Voltage stored as 0.01V."
		::= { upsApm160snmpEntry 500 }
upsApm160snmp_501_Branch17Current OBJECT-TYPE
		SYNTAX Integer32
		
		MAX-ACCESS read-only
		STATUS current
		DESCRIPTION
		"upsApm160snmp_501_Branch17Current stored as 0.01A."
		::= { upsApm160snmpEntry 501 }
upsApm160snmp_502_Branch17Energy OBJECT-TYPE
		SYNTAX Integer32
		
		MAX-ACCESS read-only
		STATUS current
		DESCRIPTION
		"upsApm160snmp_502_Branch17Energy stored as 0.01kWh."
		::= { upsApm160snmpEntry 502 }
upsApm160snmp_503_Branch17SwitchStatus OBJECT-TYPE
		SYNTAX INTEGER {
			open(0),
			close(1) }
		MAX-ACCESS read-only
		STATUS current
		DESCRIPTION
		"upsApm160snmp_503_Branch17SwitchStatus status."
		::= { upsApm160snmpEntry 503 }
upsApm160snmp_504_Branch17ActivePower OBJECT-TYPE
		SYNTAX Integer32
		
		MAX-ACCESS read-only
		STATUS current
		DESCRIPTION
		"upsApm160snmp_504_Branch17ActivePower stored as 0.01kW."
		::= { upsApm160snmpEntry 504 }
upsApm160snmp_505_Branch17ApparentPower OBJECT-TYPE
		SYNTAX Integer32
		
		MAX-ACCESS read-only
		STATUS current
		DESCRIPTION
		"upsApm160snmp_505_Branch17ApparentPower stored as 0.01kVA."
		::= { upsApm160snmpEntry 505 }
upsApm160snmp_506_Branch17THDi OBJECT-TYPE
		SYNTAX Integer32
		
		MAX-ACCESS read-only
		STATUS current
		DESCRIPTION
		"upsApm160snmp_506_Branch17THDi stored as 0.01%."
		::= { upsApm160snmpEntry 506 }
upsApm160snmp_507_Branch17RatedCurrent OBJECT-TYPE
		SYNTAX Integer32
		
		MAX-ACCESS read-only
		STATUS current
		DESCRIPTION
		"upsApm160snmp_507_Branch17RatedCurrent stored as 0.01A."
		::= { upsApm160snmpEntry 507 }
upsApm160snmp_508_Branch17LoadRatio OBJECT-TYPE
		SYNTAX Integer32
		
		MAX-ACCESS read-only
		STATUS current
		DESCRIPTION
		"upsApm160snmp_508_Branch17LoadRatio stored as 0.01%."
		::= { upsApm160snmpEntry 508 }
upsApm160snmp_509_Branch17PowerFactor OBJECT-TYPE
		SYNTAX Integer32
		
		MAX-ACCESS read-only
		STATUS current
		DESCRIPTION
		"upsApm160snmp_509_Branch17PowerFactor stored as 0.01."
		::= { upsApm160snmpEntry 509 }
upsApm160snmp_510_Branch17Voltage OBJECT-TYPE
		SYNTAX Integer32
		
		MAX-ACCESS read-only
		STATUS current
		DESCRIPTION
		"upsApm160snmp_510_Branch17Voltage stored as 0.01V."
		::= { upsApm160snmpEntry 510 }
upsApm160snmp_511_Branch18Current OBJECT-TYPE
		SYNTAX Integer32
		
		MAX-ACCESS read-only
		STATUS current
		DESCRIPTION
		"upsApm160snmp_511_Branch18Current stored as 0.01A."
		::= { upsApm160snmpEntry 511 }
upsApm160snmp_512_Branch18Energy OBJECT-TYPE
		SYNTAX Integer32
		
		MAX-ACCESS read-only
		STATUS current
		DESCRIPTION
		"upsApm160snmp_512_Branch18Energy stored as 0.01kWh."
		::= { upsApm160snmpEntry 512 }
upsApm160snmp_513_Branch18SwitchStatus OBJECT-TYPE
		SYNTAX INTEGER {
			open(0),
			close(1) }
		MAX-ACCESS read-only
		STATUS current
		DESCRIPTION
		"upsApm160snmp_513_Branch18SwitchStatus status."
		::= { upsApm160snmpEntry 513 }
upsApm160snmp_514_Branch18ActivePower OBJECT-TYPE
		SYNTAX Integer32
		
		MAX-ACCESS read-only
		STATUS current
		DESCRIPTION
		"upsApm160snmp_514_Branch18ActivePower stored as 0.01kW."
		::= { upsApm160snmpEntry 514 }
upsApm160snmp_515_Branch18ApparentPower OBJECT-TYPE
		SYNTAX Integer32
		
		MAX-ACCESS read-only
		STATUS current
		DESCRIPTION
		"upsApm160snmp_515_Branch18ApparentPower stored as 0.01kVA."
		::= { upsApm160snmpEntry 515 }
upsApm160snmp_516_Branch18THDi OBJECT-TYPE
		SYNTAX Integer32
		
		MAX-ACCESS read-only
		STATUS current
		DESCRIPTION
		"upsApm160snmp_516_Branch18THDi stored as 0.01%."
		::= { upsApm160snmpEntry 516 }
upsApm160snmp_517_Branch18RatedCurrent OBJECT-TYPE
		SYNTAX Integer32
		
		MAX-ACCESS read-only
		STATUS current
		DESCRIPTION
		"upsApm160snmp_517_Branch18RatedCurrent stored as 0.01A."
		::= { upsApm160snmpEntry 517 }
upsApm160snmp_518_Branch18LoadRatio OBJECT-TYPE
		SYNTAX Integer32
		
		MAX-ACCESS read-only
		STATUS current
		DESCRIPTION
		"upsApm160snmp_518_Branch18LoadRatio stored as 0.01%."
		::= { upsApm160snmpEntry 518 }
upsApm160snmp_519_Branch18PowerFactor OBJECT-TYPE
		SYNTAX Integer32
		
		MAX-ACCESS read-only
		STATUS current
		DESCRIPTION
		"upsApm160snmp_519_Branch18PowerFactor stored as 0.01."
		::= { upsApm160snmpEntry 519 }
upsApm160snmp_520_Branch18Voltage OBJECT-TYPE
		SYNTAX Integer32
		
		MAX-ACCESS read-only
		STATUS current
		DESCRIPTION
		"upsApm160snmp_520_Branch18Voltage stored as 0.01V."
		::= { upsApm160snmpEntry 520 }
upsApm160snmp_521_Branch19Current OBJECT-TYPE
		SYNTAX Integer32
		
		MAX-ACCESS read-only
		STATUS current
		DESCRIPTION
		"upsApm160snmp_521_Branch19Current stored as 0.01A."
		::= { upsApm160snmpEntry 521 }
upsApm160snmp_522_Branch19Energy OBJECT-TYPE
		SYNTAX Integer32
		
		MAX-ACCESS read-only
		STATUS current
		DESCRIPTION
		"upsApm160snmp_522_Branch19Energy stored as 0.01kWh."
		::= { upsApm160snmpEntry 522 }
upsApm160snmp_523_Branch19SwitchStatus OBJECT-TYPE
		SYNTAX INTEGER {
			open(0),
			close(1) }
		MAX-ACCESS read-only
		STATUS current
		DESCRIPTION
		"upsApm160snmp_523_Branch19SwitchStatus status."
		::= { upsApm160snmpEntry 523 }
upsApm160snmp_524_Branch19ActivePower OBJECT-TYPE
		SYNTAX Integer32
		
		MAX-ACCESS read-only
		STATUS current
		DESCRIPTION
		"upsApm160snmp_524_Branch19ActivePower stored as 0.01kW."
		::= { upsApm160snmpEntry 524 }
upsApm160snmp_525_Branch19ApparentPower OBJECT-TYPE
		SYNTAX Integer32
		
		MAX-ACCESS read-only
		STATUS current
		DESCRIPTION
		"upsApm160snmp_525_Branch19ApparentPower stored as 0.01kVA."
		::= { upsApm160snmpEntry 525 }
upsApm160snmp_526_Branch19THDi OBJECT-TYPE
		SYNTAX Integer32
		
		MAX-ACCESS read-only
		STATUS current
		DESCRIPTION
		"upsApm160snmp_526_Branch19THDi stored as 0.01%."
		::= { upsApm160snmpEntry 526 }
upsApm160snmp_527_Branch19RatedCurrent OBJECT-TYPE
		SYNTAX Integer32
		
		MAX-ACCESS read-only
		STATUS current
		DESCRIPTION
		"upsApm160snmp_527_Branch19RatedCurrent stored as 0.01A."
		::= { upsApm160snmpEntry 527 }
upsApm160snmp_528_Branch19LoadRatio OBJECT-TYPE
		SYNTAX Integer32
		
		MAX-ACCESS read-only
		STATUS current
		DESCRIPTION
		"upsApm160snmp_528_Branch19LoadRatio stored as 0.01%."
		::= { upsApm160snmpEntry 528 }
upsApm160snmp_529_Branch19PowerFactor OBJECT-TYPE
		SYNTAX Integer32
		
		MAX-ACCESS read-only
		STATUS current
		DESCRIPTION
		"upsApm160snmp_529_Branch19PowerFactor stored as 0.01."
		::= { upsApm160snmpEntry 529 }
upsApm160snmp_530_Branch19Voltage OBJECT-TYPE
		SYNTAX Integer32
		
		MAX-ACCESS read-only
		STATUS current
		DESCRIPTION
		"upsApm160snmp_530_Branch19Voltage stored as 0.01V."
		::= { upsApm160snmpEntry 530 }
upsApm160snmp_531_Branch20Current OBJECT-TYPE
		SYNTAX Integer32
		
		MAX-ACCESS read-only
		STATUS current
		DESCRIPTION
		"upsApm160snmp_531_Branch20Current stored as 0.01A."
		::= { upsApm160snmpEntry 531 }
upsApm160snmp_532_Branch20Energy OBJECT-TYPE
		SYNTAX Integer32
		
		MAX-ACCESS read-only
		STATUS current
		DESCRIPTION
		"upsApm160snmp_532_Branch20Energy stored as 0.01kWh."
		::= { upsApm160snmpEntry 532 }
upsApm160snmp_533_Branch20SwitchStatus OBJECT-TYPE
		SYNTAX INTEGER {
			open(0),
			close(1) }
		MAX-ACCESS read-only
		STATUS current
		DESCRIPTION
		"upsApm160snmp_533_Branch20SwitchStatus status."
		::= { upsApm160snmpEntry 533 }
upsApm160snmp_534_Branch20ActivePower OBJECT-TYPE
		SYNTAX Integer32
		
		MAX-ACCESS read-only
		STATUS current
		DESCRIPTION
		"upsApm160snmp_534_Branch20ActivePower stored as 0.01kW."
		::= { upsApm160snmpEntry 534 }
upsApm160snmp_535_Branch20ApparentPower OBJECT-TYPE
		SYNTAX Integer32
		
		MAX-ACCESS read-only
		STATUS current
		DESCRIPTION
		"upsApm160snmp_535_Branch20ApparentPower stored as 0.01kVA."
		::= { upsApm160snmpEntry 535 }
upsApm160snmp_536_Branch20THDi OBJECT-TYPE
		SYNTAX Integer32
		
		MAX-ACCESS read-only
		STATUS current
		DESCRIPTION
		"upsApm160snmp_536_Branch20THDi stored as 0.01%."
		::= { upsApm160snmpEntry 536 }
upsApm160snmp_537_Branch20RatedCurrent OBJECT-TYPE
		SYNTAX Integer32
		
		MAX-ACCESS read-only
		STATUS current
		DESCRIPTION
		"upsApm160snmp_537_Branch20RatedCurrent stored as 0.01A."
		::= { upsApm160snmpEntry 537 }
upsApm160snmp_538_Branch20LoadRatio OBJECT-TYPE
		SYNTAX Integer32
		
		MAX-ACCESS read-only
		STATUS current
		DESCRIPTION
		"upsApm160snmp_538_Branch20LoadRatio stored as 0.01%."
		::= { upsApm160snmpEntry 538 }
upsApm160snmp_539_Branch20PowerFactor OBJECT-TYPE
		SYNTAX Integer32
		
		MAX-ACCESS read-only
		STATUS current
		DESCRIPTION
		"upsApm160snmp_539_Branch20PowerFactor stored as 0.01."
		::= { upsApm160snmpEntry 539 }
upsApm160snmp_540_Branch20Voltage OBJECT-TYPE
		SYNTAX Integer32
		
		MAX-ACCESS read-only
		STATUS current
		DESCRIPTION
		"upsApm160snmp_540_Branch20Voltage stored as 0.01V."
		::= { upsApm160snmpEntry 540 }
upsApm160snmp_541_Branch21Current OBJECT-TYPE
		SYNTAX Integer32
		
		MAX-ACCESS read-only
		STATUS current
		DESCRIPTION
		"upsApm160snmp_541_Branch21Current stored as 0.01A."
		::= { upsApm160snmpEntry 541 }
upsApm160snmp_542_Branch21Energy OBJECT-TYPE
		SYNTAX Integer32
		
		MAX-ACCESS read-only
		STATUS current
		DESCRIPTION
		"upsApm160snmp_542_Branch21Energy stored as 0.01kWh."
		::= { upsApm160snmpEntry 542 }
upsApm160snmp_543_Branch21SwitchStatus OBJECT-TYPE
		SYNTAX INTEGER {
			open(0),
			close(1) }
		MAX-ACCESS read-only
		STATUS current
		DESCRIPTION
		"upsApm160snmp_543_Branch21SwitchStatus status."
		::= { upsApm160snmpEntry 543 }
upsApm160snmp_544_Branch21ActivePower OBJECT-TYPE
		SYNTAX Integer32
		
		MAX-ACCESS read-only
		STATUS current
		DESCRIPTION
		"upsApm160snmp_544_Branch21ActivePower stored as 0.01kW."
		::= { upsApm160snmpEntry 544 }
upsApm160snmp_545_Branch21ApparentPower OBJECT-TYPE
		SYNTAX Integer32
		
		MAX-ACCESS read-only
		STATUS current
		DESCRIPTION
		"upsApm160snmp_545_Branch21ApparentPower stored as 0.01kVA."
		::= { upsApm160snmpEntry 545 }
upsApm160snmp_546_Branch21THDi OBJECT-TYPE
		SYNTAX Integer32
		
		MAX-ACCESS read-only
		STATUS current
		DESCRIPTION
		"upsApm160snmp_546_Branch21THDi stored as 0.01%."
		::= { upsApm160snmpEntry 546 }
upsApm160snmp_547_Branch21RatedCurrent OBJECT-TYPE
		SYNTAX Integer32
		
		MAX-ACCESS read-only
		STATUS current
		DESCRIPTION
		"upsApm160snmp_547_Branch21RatedCurrent stored as 0.01A."
		::= { upsApm160snmpEntry 547 }
upsApm160snmp_548_Branch21LoadRatio OBJECT-TYPE
		SYNTAX Integer32
		
		MAX-ACCESS read-only
		STATUS current
		DESCRIPTION
		"upsApm160snmp_548_Branch21LoadRatio stored as 0.01%."
		::= { upsApm160snmpEntry 548 }
upsApm160snmp_549_Branch21PowerFactor OBJECT-TYPE
		SYNTAX Integer32
		
		MAX-ACCESS read-only
		STATUS current
		DESCRIPTION
		"upsApm160snmp_549_Branch21PowerFactor stored as 0.01."
		::= { upsApm160snmpEntry 549 }
upsApm160snmp_550_Branch21Voltage OBJECT-TYPE
		SYNTAX Integer32
		
		MAX-ACCESS read-only
		STATUS current
		DESCRIPTION
		"upsApm160snmp_550_Branch21Voltage stored as 0.01V."
		::= { upsApm160snmpEntry 550 }
upsApm160snmp_551_Branch22Current OBJECT-TYPE
		SYNTAX Integer32
		
		MAX-ACCESS read-only
		STATUS current
		DESCRIPTION
		"upsApm160snmp_551_Branch22Current stored as 0.01A."
		::= { upsApm160snmpEntry 551 }
upsApm160snmp_552_Branch22Energy OBJECT-TYPE
		SYNTAX Integer32
		
		MAX-ACCESS read-only
		STATUS current
		DESCRIPTION
		"upsApm160snmp_552_Branch22Energy stored as 0.01kWh."
		::= { upsApm160snmpEntry 552 }
upsApm160snmp_553_Branch22SwitchStatus OBJECT-TYPE
		SYNTAX INTEGER {
			open(0),
			close(1) }
		MAX-ACCESS read-only
		STATUS current
		DESCRIPTION
		"upsApm160snmp_553_Branch22SwitchStatus status."
		::= { upsApm160snmpEntry 553 }
upsApm160snmp_554_Branch22ActivePower OBJECT-TYPE
		SYNTAX Integer32
		
		MAX-ACCESS read-only
		STATUS current
		DESCRIPTION
		"upsApm160snmp_554_Branch22ActivePower stored as 0.01kW."
		::= { upsApm160snmpEntry 554 }
upsApm160snmp_555_Branch22ApparentPower OBJECT-TYPE
		SYNTAX Integer32
		
		MAX-ACCESS read-only
		STATUS current
		DESCRIPTION
		"upsApm160snmp_555_Branch22ApparentPower stored as 0.01kVA."
		::= { upsApm160snmpEntry 555 }
upsApm160snmp_556_Branch22THDi OBJECT-TYPE
		SYNTAX Integer32
		
		MAX-ACCESS read-only
		STATUS current
		DESCRIPTION
		"upsApm160snmp_556_Branch22THDi stored as 0.01%."
		::= { upsApm160snmpEntry 556 }
upsApm160snmp_557_Branch22RatedCurrent OBJECT-TYPE
		SYNTAX Integer32
		
		MAX-ACCESS read-only
		STATUS current
		DESCRIPTION
		"upsApm160snmp_557_Branch22RatedCurrent stored as 0.01A."
		::= { upsApm160snmpEntry 557 }
upsApm160snmp_558_Branch22LoadRatio OBJECT-TYPE
		SYNTAX Integer32
		
		MAX-ACCESS read-only
		STATUS current
		DESCRIPTION
		"upsApm160snmp_558_Branch22LoadRatio stored as 0.01%."
		::= { upsApm160snmpEntry 558 }
upsApm160snmp_559_Branch22PowerFactor OBJECT-TYPE
		SYNTAX Integer32
		
		MAX-ACCESS read-only
		STATUS current
		DESCRIPTION
		"upsApm160snmp_559_Branch22PowerFactor stored as 0.01."
		::= { upsApm160snmpEntry 559 }
upsApm160snmp_560_Branch22Voltage OBJECT-TYPE
		SYNTAX Integer32
		
		MAX-ACCESS read-only
		STATUS current
		DESCRIPTION
		"upsApm160snmp_560_Branch22Voltage stored as 0.01V."
		::= { upsApm160snmpEntry 560 }
upsApm160snmp_561_Branch23Current OBJECT-TYPE
		SYNTAX Integer32
		
		MAX-ACCESS read-only
		STATUS current
		DESCRIPTION
		"upsApm160snmp_561_Branch23Current stored as 0.01A."
		::= { upsApm160snmpEntry 561 }
upsApm160snmp_562_Branch23Energy OBJECT-TYPE
		SYNTAX Integer32
		
		MAX-ACCESS read-only
		STATUS current
		DESCRIPTION
		"upsApm160snmp_562_Branch23Energy stored as 0.01kWh."
		::= { upsApm160snmpEntry 562 }
upsApm160snmp_563_Branch23SwitchStatus OBJECT-TYPE
		SYNTAX INTEGER {
			open(0),
			close(1) }
		MAX-ACCESS read-only
		STATUS current
		DESCRIPTION
		"upsApm160snmp_563_Branch23SwitchStatus status."
		::= { upsApm160snmpEntry 563 }
upsApm160snmp_564_Branch23ActivePower OBJECT-TYPE
		SYNTAX Integer32
		
		MAX-ACCESS read-only
		STATUS current
		DESCRIPTION
		"upsApm160snmp_564_Branch23ActivePower stored as 0.01kW."
		::= { upsApm160snmpEntry 564 }
upsApm160snmp_565_Branch23ApparentPower OBJECT-TYPE
		SYNTAX Integer32
		
		MAX-ACCESS read-only
		STATUS current
		DESCRIPTION
		"upsApm160snmp_565_Branch23ApparentPower stored as 0.01kVA."
		::= { upsApm160snmpEntry 565 }
upsApm160snmp_566_Branch23THDi OBJECT-TYPE
		SYNTAX Integer32
		
		MAX-ACCESS read-only
		STATUS current
		DESCRIPTION
		"upsApm160snmp_566_Branch23THDi stored as 0.01%."
		::= { upsApm160snmpEntry 566 }
upsApm160snmp_567_Branch23RatedCurrent OBJECT-TYPE
		SYNTAX Integer32
		
		MAX-ACCESS read-only
		STATUS current
		DESCRIPTION
		"upsApm160snmp_567_Branch23RatedCurrent stored as 0.01A."
		::= { upsApm160snmpEntry 567 }
upsApm160snmp_568_Branch23LoadRatio OBJECT-TYPE
		SYNTAX Integer32
		
		MAX-ACCESS read-only
		STATUS current
		DESCRIPTION
		"upsApm160snmp_568_Branch23LoadRatio stored as 0.01%."
		::= { upsApm160snmpEntry 568 }
upsApm160snmp_569_Branch23PowerFactor OBJECT-TYPE
		SYNTAX Integer32
		
		MAX-ACCESS read-only
		STATUS current
		DESCRIPTION
		"upsApm160snmp_569_Branch23PowerFactor stored as 0.01."
		::= { upsApm160snmpEntry 569 }
upsApm160snmp_570_Branch23Voltage OBJECT-TYPE
		SYNTAX Integer32
		
		MAX-ACCESS read-only
		STATUS current
		DESCRIPTION
		"upsApm160snmp_570_Branch23Voltage stored as 0.01V."
		::= { upsApm160snmpEntry 570 }
upsApm160snmp_571_Branch24Current OBJECT-TYPE
		SYNTAX Integer32
		
		MAX-ACCESS read-only
		STATUS current
		DESCRIPTION
		"upsApm160snmp_571_Branch24Current stored as 0.01A."
		::= { upsApm160snmpEntry 571 }
upsApm160snmp_572_Branch24Energy OBJECT-TYPE
		SYNTAX Integer32
		
		MAX-ACCESS read-only
		STATUS current
		DESCRIPTION
		"upsApm160snmp_572_Branch24Energy stored as 0.01kWh."
		::= { upsApm160snmpEntry 572 }
upsApm160snmp_573_Branch24SwitchStatus OBJECT-TYPE
		SYNTAX INTEGER {
			open(0),
			close(1) }
		MAX-ACCESS read-only
		STATUS current
		DESCRIPTION
		"upsApm160snmp_573_Branch24SwitchStatus status."
		::= { upsApm160snmpEntry 573 }
upsApm160snmp_574_Branch24ActivePower OBJECT-TYPE
		SYNTAX Integer32
		
		MAX-ACCESS read-only
		STATUS current
		DESCRIPTION
		"upsApm160snmp_574_Branch24ActivePower stored as 0.01kW."
		::= { upsApm160snmpEntry 574 }
upsApm160snmp_575_Branch24ApparentPower OBJECT-TYPE
		SYNTAX Integer32
		
		MAX-ACCESS read-only
		STATUS current
		DESCRIPTION
		"upsApm160snmp_575_Branch24ApparentPower stored as 0.01kVA."
		::= { upsApm160snmpEntry 575 }
upsApm160snmp_576_Branch24THDi OBJECT-TYPE
		SYNTAX Integer32
		
		MAX-ACCESS read-only
		STATUS current
		DESCRIPTION
		"upsApm160snmp_576_Branch24THDi stored as 0.01%."
		::= { upsApm160snmpEntry 576 }
upsApm160snmp_577_Branch24RatedCurrent OBJECT-TYPE
		SYNTAX Integer32
		
		MAX-ACCESS read-only
		STATUS current
		DESCRIPTION
		"upsApm160snmp_577_Branch24RatedCurrent stored as 0.01A."
		::= { upsApm160snmpEntry 577 }
upsApm160snmp_578_Branch24LoadRatio OBJECT-TYPE
		SYNTAX Integer32
		
		MAX-ACCESS read-only
		STATUS current
		DESCRIPTION
		"upsApm160snmp_578_Branch24LoadRatio stored as 0.01%."
		::= { upsApm160snmpEntry 578 }
upsApm160snmp_579_Branch24PowerFactor OBJECT-TYPE
		SYNTAX Integer32
		
		MAX-ACCESS read-only
		STATUS current
		DESCRIPTION
		"upsApm160snmp_579_Branch24PowerFactor stored as 0.01."
		::= { upsApm160snmpEntry 579 }
upsApm160snmp_580_Branch24Voltage OBJECT-TYPE
		SYNTAX Integer32
		
		MAX-ACCESS read-only
		STATUS current
		DESCRIPTION
		"upsApm160snmp_580_Branch24Voltage stored as 0.01V."
		::= { upsApm160snmpEntry 580 }
upsApm160snmp_581_Branch25Current OBJECT-TYPE
		SYNTAX Integer32
		
		MAX-ACCESS read-only
		STATUS current
		DESCRIPTION
		"upsApm160snmp_581_Branch25Current stored as 0.01A."
		::= { upsApm160snmpEntry 581 }
upsApm160snmp_582_Branch25Energy OBJECT-TYPE
		SYNTAX Integer32
		
		MAX-ACCESS read-only
		STATUS current
		DESCRIPTION
		"upsApm160snmp_582_Branch25Energy stored as 0.01kWh."
		::= { upsApm160snmpEntry 582 }
upsApm160snmp_583_Branch25SwitchStatus OBJECT-TYPE
		SYNTAX INTEGER {
			open(0),
			close(1) }
		MAX-ACCESS read-only
		STATUS current
		DESCRIPTION
		"upsApm160snmp_583_Branch25SwitchStatus status."
		::= { upsApm160snmpEntry 583 }
upsApm160snmp_584_Branch25ActivePower OBJECT-TYPE
		SYNTAX Integer32
		
		MAX-ACCESS read-only
		STATUS current
		DESCRIPTION
		"upsApm160snmp_584_Branch25ActivePower stored as 0.01kW."
		::= { upsApm160snmpEntry 584 }
upsApm160snmp_585_Branch25ApparentPower OBJECT-TYPE
		SYNTAX Integer32
		
		MAX-ACCESS read-only
		STATUS current
		DESCRIPTION
		"upsApm160snmp_585_Branch25ApparentPower stored as 0.01kVA."
		::= { upsApm160snmpEntry 585 }
upsApm160snmp_586_Branch25THDi OBJECT-TYPE
		SYNTAX Integer32
		
		MAX-ACCESS read-only
		STATUS current
		DESCRIPTION
		"upsApm160snmp_586_Branch25THDi stored as 0.01%."
		::= { upsApm160snmpEntry 586 }
upsApm160snmp_587_Branch25RatedCurrent OBJECT-TYPE
		SYNTAX Integer32
		
		MAX-ACCESS read-only
		STATUS current
		DESCRIPTION
		"upsApm160snmp_587_Branch25RatedCurrent stored as 0.01A."
		::= { upsApm160snmpEntry 587 }
upsApm160snmp_588_Branch25LoadRatio OBJECT-TYPE
		SYNTAX Integer32
		
		MAX-ACCESS read-only
		STATUS current
		DESCRIPTION
		"upsApm160snmp_588_Branch25LoadRatio stored as 0.01%."
		::= { upsApm160snmpEntry 588 }
upsApm160snmp_589_Branch25PowerFactor OBJECT-TYPE
		SYNTAX Integer32
		
		MAX-ACCESS read-only
		STATUS current
		DESCRIPTION
		"upsApm160snmp_589_Branch25PowerFactor stored as 0.01."
		::= { upsApm160snmpEntry 589 }
upsApm160snmp_590_Branch25Voltage OBJECT-TYPE
		SYNTAX Integer32
		
		MAX-ACCESS read-only
		STATUS current
		DESCRIPTION
		"upsApm160snmp_590_Branch25Voltage stored as 0.01V."
		::= { upsApm160snmpEntry 590 }
upsApm160snmp_591_Branch26Current OBJECT-TYPE
		SYNTAX Integer32
		
		MAX-ACCESS read-only
		STATUS current
		DESCRIPTION
		"upsApm160snmp_591_Branch26Current stored as 0.01A."
		::= { upsApm160snmpEntry 591 }
upsApm160snmp_592_Branch26Energy OBJECT-TYPE
		SYNTAX Integer32
		
		MAX-ACCESS read-only
		STATUS current
		DESCRIPTION
		"upsApm160snmp_592_Branch26Energy stored as 0.01kWh."
		::= { upsApm160snmpEntry 592 }
upsApm160snmp_593_Branch26SwitchStatus OBJECT-TYPE
		SYNTAX INTEGER {
			open(0),
			close(1) }
		MAX-ACCESS read-only
		STATUS current
		DESCRIPTION
		"upsApm160snmp_593_Branch26SwitchStatus status."
		::= { upsApm160snmpEntry 593 }
upsApm160snmp_594_Branch26ActivePower OBJECT-TYPE
		SYNTAX Integer32
		
		MAX-ACCESS read-only
		STATUS current
		DESCRIPTION
		"upsApm160snmp_594_Branch26ActivePower stored as 0.01kW."
		::= { upsApm160snmpEntry 594 }
upsApm160snmp_595_Branch26ApparentPower OBJECT-TYPE
		SYNTAX Integer32
		
		MAX-ACCESS read-only
		STATUS current
		DESCRIPTION
		"upsApm160snmp_595_Branch26ApparentPower stored as 0.01kVA."
		::= { upsApm160snmpEntry 595 }
upsApm160snmp_596_Branch26THDi OBJECT-TYPE
		SYNTAX Integer32
		
		MAX-ACCESS read-only
		STATUS current
		DESCRIPTION
		"upsApm160snmp_596_Branch26THDi stored as 0.01%."
		::= { upsApm160snmpEntry 596 }
upsApm160snmp_597_Branch26RatedCurrent OBJECT-TYPE
		SYNTAX Integer32
		
		MAX-ACCESS read-only
		STATUS current
		DESCRIPTION
		"upsApm160snmp_597_Branch26RatedCurrent stored as 0.01A."
		::= { upsApm160snmpEntry 597 }
upsApm160snmp_598_Branch26LoadRatio OBJECT-TYPE
		SYNTAX Integer32
		
		MAX-ACCESS read-only
		STATUS current
		DESCRIPTION
		"upsApm160snmp_598_Branch26LoadRatio stored as 0.01%."
		::= { upsApm160snmpEntry 598 }
upsApm160snmp_599_Branch26PowerFactor OBJECT-TYPE
		SYNTAX Integer32
		
		MAX-ACCESS read-only
		STATUS current
		DESCRIPTION
		"upsApm160snmp_599_Branch26PowerFactor stored as 0.01."
		::= { upsApm160snmpEntry 599 }
upsApm160snmp_600_Branch26Voltage OBJECT-TYPE
		SYNTAX Integer32
		
		MAX-ACCESS read-only
		STATUS current
		DESCRIPTION
		"upsApm160snmp_600_Branch26Voltage stored as 0.01V."
		::= { upsApm160snmpEntry 600 }
upsApm160snmp_601_Branch27Current OBJECT-TYPE
		SYNTAX Integer32
		
		MAX-ACCESS read-only
		STATUS current
		DESCRIPTION
		"upsApm160snmp_601_Branch27Current stored as 0.01A."
		::= { upsApm160snmpEntry 601 }
upsApm160snmp_602_Branch27Energy OBJECT-TYPE
		SYNTAX Integer32
		
		MAX-ACCESS read-only
		STATUS current
		DESCRIPTION
		"upsApm160snmp_602_Branch27Energy stored as 0.01kWh."
		::= { upsApm160snmpEntry 602 }
upsApm160snmp_603_Branch27SwitchStatus OBJECT-TYPE
		SYNTAX INTEGER {
			open(0),
			close(1) }
		MAX-ACCESS read-only
		STATUS current
		DESCRIPTION
		"upsApm160snmp_603_Branch27SwitchStatus status."
		::= { upsApm160snmpEntry 603 }
upsApm160snmp_604_Branch27ActivePower OBJECT-TYPE
		SYNTAX Integer32
		
		MAX-ACCESS read-only
		STATUS current
		DESCRIPTION
		"upsApm160snmp_604_Branch27ActivePower stored as 0.01kW."
		::= { upsApm160snmpEntry 604 }
upsApm160snmp_605_Branch27ApparentPower OBJECT-TYPE
		SYNTAX Integer32
		
		MAX-ACCESS read-only
		STATUS current
		DESCRIPTION
		"upsApm160snmp_605_Branch27ApparentPower stored as 0.01kVA."
		::= { upsApm160snmpEntry 605 }
upsApm160snmp_606_Branch27THDi OBJECT-TYPE
		SYNTAX Integer32
		
		MAX-ACCESS read-only
		STATUS current
		DESCRIPTION
		"upsApm160snmp_606_Branch27THDi stored as 0.01%."
		::= { upsApm160snmpEntry 606 }
upsApm160snmp_607_Branch27RatedCurrent OBJECT-TYPE
		SYNTAX Integer32
		
		MAX-ACCESS read-only
		STATUS current
		DESCRIPTION
		"upsApm160snmp_607_Branch27RatedCurrent stored as 0.01A."
		::= { upsApm160snmpEntry 607 }
upsApm160snmp_608_Branch27LoadRatio OBJECT-TYPE
		SYNTAX Integer32
		
		MAX-ACCESS read-only
		STATUS current
		DESCRIPTION
		"upsApm160snmp_608_Branch27LoadRatio stored as 0.01%."
		::= { upsApm160snmpEntry 608 }
upsApm160snmp_609_Branch27PowerFactor OBJECT-TYPE
		SYNTAX Integer32
		
		MAX-ACCESS read-only
		STATUS current
		DESCRIPTION
		"upsApm160snmp_609_Branch27PowerFactor stored as 0.01."
		::= { upsApm160snmpEntry 609 }
upsApm160snmp_610_Branch27Voltage OBJECT-TYPE
		SYNTAX Integer32
		
		MAX-ACCESS read-only
		STATUS current
		DESCRIPTION
		"upsApm160snmp_610_Branch27Voltage stored as 0.01V."
		::= { upsApm160snmpEntry 610 }
upsApm160snmp_611_Branch28Current OBJECT-TYPE
		SYNTAX Integer32
		
		MAX-ACCESS read-only
		STATUS current
		DESCRIPTION
		"upsApm160snmp_611_Branch28Current stored as 0.01A."
		::= { upsApm160snmpEntry 611 }
upsApm160snmp_612_Branch28Energy OBJECT-TYPE
		SYNTAX Integer32
		
		MAX-ACCESS read-only
		STATUS current
		DESCRIPTION
		"upsApm160snmp_612_Branch28Energy stored as 0.01kWh."
		::= { upsApm160snmpEntry 612 }
upsApm160snmp_613_Branch28SwitchStatus OBJECT-TYPE
		SYNTAX INTEGER {
			open(0),
			close(1) }
		MAX-ACCESS read-only
		STATUS current
		DESCRIPTION
		"upsApm160snmp_613_Branch28SwitchStatus status."
		::= { upsApm160snmpEntry 613 }
upsApm160snmp_614_Branch28ActivePower OBJECT-TYPE
		SYNTAX Integer32
		
		MAX-ACCESS read-only
		STATUS current
		DESCRIPTION
		"upsApm160snmp_614_Branch28ActivePower stored as 0.01kW."
		::= { upsApm160snmpEntry 614 }
upsApm160snmp_615_Branch28ApparentPower OBJECT-TYPE
		SYNTAX Integer32
		
		MAX-ACCESS read-only
		STATUS current
		DESCRIPTION
		"upsApm160snmp_615_Branch28ApparentPower stored as 0.01kVA."
		::= { upsApm160snmpEntry 615 }
upsApm160snmp_616_Branch28THDi OBJECT-TYPE
		SYNTAX Integer32
		
		MAX-ACCESS read-only
		STATUS current
		DESCRIPTION
		"upsApm160snmp_616_Branch28THDi stored as 0.01%."
		::= { upsApm160snmpEntry 616 }
upsApm160snmp_617_Branch28RatedCurrent OBJECT-TYPE
		SYNTAX Integer32
		
		MAX-ACCESS read-only
		STATUS current
		DESCRIPTION
		"upsApm160snmp_617_Branch28RatedCurrent stored as 0.01A."
		::= { upsApm160snmpEntry 617 }
upsApm160snmp_618_Branch28LoadRatio OBJECT-TYPE
		SYNTAX Integer32
		
		MAX-ACCESS read-only
		STATUS current
		DESCRIPTION
		"upsApm160snmp_618_Branch28LoadRatio stored as 0.01%."
		::= { upsApm160snmpEntry 618 }
upsApm160snmp_619_Branch28PowerFactor OBJECT-TYPE
		SYNTAX Integer32
		
		MAX-ACCESS read-only
		STATUS current
		DESCRIPTION
		"upsApm160snmp_619_Branch28PowerFactor stored as 0.01."
		::= { upsApm160snmpEntry 619 }
upsApm160snmp_620_Branch28Voltage OBJECT-TYPE
		SYNTAX Integer32
		
		MAX-ACCESS read-only
		STATUS current
		DESCRIPTION
		"upsApm160snmp_620_Branch28Voltage stored as 0.01V."
		::= { upsApm160snmpEntry 620 }
upsApm160snmp_621_Branch29Current OBJECT-TYPE
		SYNTAX Integer32
		
		MAX-ACCESS read-only
		STATUS current
		DESCRIPTION
		"upsApm160snmp_621_Branch29Current stored as 0.01A."
		::= { upsApm160snmpEntry 621 }
upsApm160snmp_622_Branch29Energy OBJECT-TYPE
		SYNTAX Integer32
		
		MAX-ACCESS read-only
		STATUS current
		DESCRIPTION
		"upsApm160snmp_622_Branch29Energy stored as 0.01kWh."
		::= { upsApm160snmpEntry 622 }
upsApm160snmp_623_Branch29SwitchStatus OBJECT-TYPE
		SYNTAX INTEGER {
			open(0),
			close(1) }
		MAX-ACCESS read-only
		STATUS current
		DESCRIPTION
		"upsApm160snmp_623_Branch29SwitchStatus status."
		::= { upsApm160snmpEntry 623 }
upsApm160snmp_624_Branch29ActivePower OBJECT-TYPE
		SYNTAX Integer32
		
		MAX-ACCESS read-only
		STATUS current
		DESCRIPTION
		"upsApm160snmp_624_Branch29ActivePower stored as 0.01kW."
		::= { upsApm160snmpEntry 624 }
upsApm160snmp_625_Branch29ApparentPower OBJECT-TYPE
		SYNTAX Integer32
		
		MAX-ACCESS read-only
		STATUS current
		DESCRIPTION
		"upsApm160snmp_625_Branch29ApparentPower stored as 0.01kVA."
		::= { upsApm160snmpEntry 625 }
upsApm160snmp_626_Branch29THDi OBJECT-TYPE
		SYNTAX Integer32
		
		MAX-ACCESS read-only
		STATUS current
		DESCRIPTION
		"upsApm160snmp_626_Branch29THDi stored as 0.01%."
		::= { upsApm160snmpEntry 626 }
upsApm160snmp_627_Branch29RatedCurrent OBJECT-TYPE
		SYNTAX Integer32
		
		MAX-ACCESS read-only
		STATUS current
		DESCRIPTION
		"upsApm160snmp_627_Branch29RatedCurrent stored as 0.01A."
		::= { upsApm160snmpEntry 627 }
upsApm160snmp_628_Branch29LoadRatio OBJECT-TYPE
		SYNTAX Integer32
		
		MAX-ACCESS read-only
		STATUS current
		DESCRIPTION
		"upsApm160snmp_628_Branch29LoadRatio stored as 0.01%."
		::= { upsApm160snmpEntry 628 }
upsApm160snmp_629_Branch29PowerFactor OBJECT-TYPE
		SYNTAX Integer32
		
		MAX-ACCESS read-only
		STATUS current
		DESCRIPTION
		"upsApm160snmp_629_Branch29PowerFactor stored as 0.01."
		::= { upsApm160snmpEntry 629 }
upsApm160snmp_630_Branch29Voltage OBJECT-TYPE
		SYNTAX Integer32
		
		MAX-ACCESS read-only
		STATUS current
		DESCRIPTION
		"upsApm160snmp_630_Branch29Voltage stored as 0.01V."
		::= { upsApm160snmpEntry 630 }
upsApm160snmp_631_Branch30Current OBJECT-TYPE
		SYNTAX Integer32
		
		MAX-ACCESS read-only
		STATUS current
		DESCRIPTION
		"upsApm160snmp_631_Branch30Current stored as 0.01A."
		::= { upsApm160snmpEntry 631 }
upsApm160snmp_632_Branch30Energy OBJECT-TYPE
		SYNTAX Integer32
		
		MAX-ACCESS read-only
		STATUS current
		DESCRIPTION
		"upsApm160snmp_632_Branch30Energy stored as 0.01kWh."
		::= { upsApm160snmpEntry 632 }
upsApm160snmp_633_Branch30SwitchStatus OBJECT-TYPE
		SYNTAX INTEGER {
			open(0),
			close(1) }
		MAX-ACCESS read-only
		STATUS current
		DESCRIPTION
		"upsApm160snmp_633_Branch30SwitchStatus status."
		::= { upsApm160snmpEntry 633 }
upsApm160snmp_634_Branch30ActivePower OBJECT-TYPE
		SYNTAX Integer32
		
		MAX-ACCESS read-only
		STATUS current
		DESCRIPTION
		"upsApm160snmp_634_Branch30ActivePower stored as 0.01kW."
		::= { upsApm160snmpEntry 634 }
upsApm160snmp_635_Branch30ApparentPower OBJECT-TYPE
		SYNTAX Integer32
		
		MAX-ACCESS read-only
		STATUS current
		DESCRIPTION
		"upsApm160snmp_635_Branch30ApparentPower stored as 0.01kVA."
		::= { upsApm160snmpEntry 635 }
upsApm160snmp_636_Branch30THDi OBJECT-TYPE
		SYNTAX Integer32
		
		MAX-ACCESS read-only
		STATUS current
		DESCRIPTION
		"upsApm160snmp_636_Branch30THDi stored as 0.01%."
		::= { upsApm160snmpEntry 636 }
upsApm160snmp_637_Branch30RatedCurrent OBJECT-TYPE
		SYNTAX Integer32
		
		MAX-ACCESS read-only
		STATUS current
		DESCRIPTION
		"upsApm160snmp_637_Branch30RatedCurrent stored as 0.01A."
		::= { upsApm160snmpEntry 637 }
upsApm160snmp_638_Branch30LoadRatio OBJECT-TYPE
		SYNTAX Integer32
		
		MAX-ACCESS read-only
		STATUS current
		DESCRIPTION
		"upsApm160snmp_638_Branch30LoadRatio stored as 0.01%."
		::= { upsApm160snmpEntry 638 }
upsApm160snmp_639_Branch30PowerFactor OBJECT-TYPE
		SYNTAX Integer32
		
		MAX-ACCESS read-only
		STATUS current
		DESCRIPTION
		"upsApm160snmp_639_Branch30PowerFactor stored as 0.01."
		::= { upsApm160snmpEntry 639 }
upsApm160snmp_640_Branch30Voltage OBJECT-TYPE
		SYNTAX Integer32
		
		MAX-ACCESS read-only
		STATUS current
		DESCRIPTION
		"upsApm160snmp_640_Branch30Voltage stored as 0.01V."
		::= { upsApm160snmpEntry 640 }
upsApm160snmp_641_Branch31Current OBJECT-TYPE
		SYNTAX Integer32
		
		MAX-ACCESS read-only
		STATUS current
		DESCRIPTION
		"upsApm160snmp_641_Branch31Current stored as 0.01A."
		::= { upsApm160snmpEntry 641 }
upsApm160snmp_642_Branch31Energy OBJECT-TYPE
		SYNTAX Integer32
		
		MAX-ACCESS read-only
		STATUS current
		DESCRIPTION
		"upsApm160snmp_642_Branch31Energy stored as 0.01kWh."
		::= { upsApm160snmpEntry 642 }
upsApm160snmp_643_Branch31SwitchStatus OBJECT-TYPE
		SYNTAX INTEGER {
			open(0),
			close(1) }
		MAX-ACCESS read-only
		STATUS current
		DESCRIPTION
		"upsApm160snmp_643_Branch31SwitchStatus status."
		::= { upsApm160snmpEntry 643 }
upsApm160snmp_644_Branch31ActivePower OBJECT-TYPE
		SYNTAX Integer32
		
		MAX-ACCESS read-only
		STATUS current
		DESCRIPTION
		"upsApm160snmp_644_Branch31ActivePower stored as 0.01kW."
		::= { upsApm160snmpEntry 644 }
upsApm160snmp_645_Branch31ApparentPower OBJECT-TYPE
		SYNTAX Integer32
		
		MAX-ACCESS read-only
		STATUS current
		DESCRIPTION
		"upsApm160snmp_645_Branch31ApparentPower stored as 0.01kVA."
		::= { upsApm160snmpEntry 645 }
upsApm160snmp_646_Branch31THDi OBJECT-TYPE
		SYNTAX Integer32
		
		MAX-ACCESS read-only
		STATUS current
		DESCRIPTION
		"upsApm160snmp_646_Branch31THDi stored as 0.01%."
		::= { upsApm160snmpEntry 646 }
upsApm160snmp_647_Branch31RatedCurrent OBJECT-TYPE
		SYNTAX Integer32
		
		MAX-ACCESS read-only
		STATUS current
		DESCRIPTION
		"upsApm160snmp_647_Branch31RatedCurrent stored as 0.01A."
		::= { upsApm160snmpEntry 647 }
upsApm160snmp_648_Branch31LoadRatio OBJECT-TYPE
		SYNTAX Integer32
		
		MAX-ACCESS read-only
		STATUS current
		DESCRIPTION
		"upsApm160snmp_648_Branch31LoadRatio stored as 0.01%."
		::= { upsApm160snmpEntry 648 }
upsApm160snmp_649_Branch31PowerFactor OBJECT-TYPE
		SYNTAX Integer32
		
		MAX-ACCESS read-only
		STATUS current
		DESCRIPTION
		"upsApm160snmp_649_Branch31PowerFactor stored as 0.01."
		::= { upsApm160snmpEntry 649 }
upsApm160snmp_650_Branch31Voltage OBJECT-TYPE
		SYNTAX Integer32
		
		MAX-ACCESS read-only
		STATUS current
		DESCRIPTION
		"upsApm160snmp_650_Branch31Voltage stored as 0.01V."
		::= { upsApm160snmpEntry 650 }
upsApm160snmp_651_Branch32Current OBJECT-TYPE
		SYNTAX Integer32
		
		MAX-ACCESS read-only
		STATUS current
		DESCRIPTION
		"upsApm160snmp_651_Branch32Current stored as 0.01A."
		::= { upsApm160snmpEntry 651 }
upsApm160snmp_652_Branch32Energy OBJECT-TYPE
		SYNTAX Integer32
		
		MAX-ACCESS read-only
		STATUS current
		DESCRIPTION
		"upsApm160snmp_652_Branch32Energy stored as 0.01kWh."
		::= { upsApm160snmpEntry 652 }
upsApm160snmp_653_Branch32SwitchStatus OBJECT-TYPE
		SYNTAX INTEGER {
			open(0),
			close(1) }
		MAX-ACCESS read-only
		STATUS current
		DESCRIPTION
		"upsApm160snmp_653_Branch32SwitchStatus status."
		::= { upsApm160snmpEntry 653 }
upsApm160snmp_654_Branch32ActivePower OBJECT-TYPE
		SYNTAX Integer32
		
		MAX-ACCESS read-only
		STATUS current
		DESCRIPTION
		"upsApm160snmp_654_Branch32ActivePower stored as 0.01kW."
		::= { upsApm160snmpEntry 654 }
upsApm160snmp_655_Branch32ApparentPower OBJECT-TYPE
		SYNTAX Integer32
		
		MAX-ACCESS read-only
		STATUS current
		DESCRIPTION
		"upsApm160snmp_655_Branch32ApparentPower stored as 0.01kVA."
		::= { upsApm160snmpEntry 655 }
upsApm160snmp_656_Branch32THDi OBJECT-TYPE
		SYNTAX Integer32
		
		MAX-ACCESS read-only
		STATUS current
		DESCRIPTION
		"upsApm160snmp_656_Branch32THDi stored as 0.01%."
		::= { upsApm160snmpEntry 656 }
upsApm160snmp_657_Branch32RatedCurrent OBJECT-TYPE
		SYNTAX Integer32
		
		MAX-ACCESS read-only
		STATUS current
		DESCRIPTION
		"upsApm160snmp_657_Branch32RatedCurrent stored as 0.01A."
		::= { upsApm160snmpEntry 657 }
upsApm160snmp_658_Branch32LoadRatio OBJECT-TYPE
		SYNTAX Integer32
		
		MAX-ACCESS read-only
		STATUS current
		DESCRIPTION
		"upsApm160snmp_658_Branch32LoadRatio stored as 0.01%."
		::= { upsApm160snmpEntry 658 }
upsApm160snmp_659_Branch32PowerFactor OBJECT-TYPE
		SYNTAX Integer32
		
		MAX-ACCESS read-only
		STATUS current
		DESCRIPTION
		"upsApm160snmp_659_Branch32PowerFactor stored as 0.01."
		::= { upsApm160snmpEntry 659 }
upsApm160snmp_660_Branch32Voltage OBJECT-TYPE
		SYNTAX Integer32
		
		MAX-ACCESS read-only
		STATUS current
		DESCRIPTION
		"upsApm160snmp_660_Branch32Voltage stored as 0.01V."
		::= { upsApm160snmpEntry 660 }
upsApm160snmp_661_Branch33Current OBJECT-TYPE
		SYNTAX Integer32
		
		MAX-ACCESS read-only
		STATUS current
		DESCRIPTION
		"upsApm160snmp_661_Branch33Current stored as 0.01A."
		::= { upsApm160snmpEntry 661 }
upsApm160snmp_662_Branch33Energy OBJECT-TYPE
		SYNTAX Integer32
		
		MAX-ACCESS read-only
		STATUS current
		DESCRIPTION
		"upsApm160snmp_662_Branch33Energy stored as 0.01kWh."
		::= { upsApm160snmpEntry 662 }
upsApm160snmp_663_Branch33SwitchStatus OBJECT-TYPE
		SYNTAX INTEGER {
			open(0),
			close(1) }
		MAX-ACCESS read-only
		STATUS current
		DESCRIPTION
		"upsApm160snmp_663_Branch33SwitchStatus status."
		::= { upsApm160snmpEntry 663 }
upsApm160snmp_664_Branch33ActivePower OBJECT-TYPE
		SYNTAX Integer32
		
		MAX-ACCESS read-only
		STATUS current
		DESCRIPTION
		"upsApm160snmp_664_Branch33ActivePower stored as 0.01kW."
		::= { upsApm160snmpEntry 664 }
upsApm160snmp_665_Branch33ApparentPower OBJECT-TYPE
		SYNTAX Integer32
		
		MAX-ACCESS read-only
		STATUS current
		DESCRIPTION
		"upsApm160snmp_665_Branch33ApparentPower stored as 0.01kVA."
		::= { upsApm160snmpEntry 665 }
upsApm160snmp_666_Branch33THDi OBJECT-TYPE
		SYNTAX Integer32
		
		MAX-ACCESS read-only
		STATUS current
		DESCRIPTION
		"upsApm160snmp_666_Branch33THDi stored as 0.01%."
		::= { upsApm160snmpEntry 666 }
upsApm160snmp_667_Branch33RatedCurrent OBJECT-TYPE
		SYNTAX Integer32
		
		MAX-ACCESS read-only
		STATUS current
		DESCRIPTION
		"upsApm160snmp_667_Branch33RatedCurrent stored as 0.01A."
		::= { upsApm160snmpEntry 667 }
upsApm160snmp_668_Branch33LoadRatio OBJECT-TYPE
		SYNTAX Integer32
		
		MAX-ACCESS read-only
		STATUS current
		DESCRIPTION
		"upsApm160snmp_668_Branch33LoadRatio stored as 0.01%."
		::= { upsApm160snmpEntry 668 }
upsApm160snmp_669_Branch33PowerFactor OBJECT-TYPE
		SYNTAX Integer32
		
		MAX-ACCESS read-only
		STATUS current
		DESCRIPTION
		"upsApm160snmp_669_Branch33PowerFactor stored as 0.01."
		::= { upsApm160snmpEntry 669 }
upsApm160snmp_670_Branch33Voltage OBJECT-TYPE
		SYNTAX Integer32
		
		MAX-ACCESS read-only
		STATUS current
		DESCRIPTION
		"upsApm160snmp_670_Branch33Voltage stored as 0.01V."
		::= { upsApm160snmpEntry 670 }
upsApm160snmp_671_Branch34Current OBJECT-TYPE
		SYNTAX Integer32
		
		MAX-ACCESS read-only
		STATUS current
		DESCRIPTION
		"upsApm160snmp_671_Branch34Current stored as 0.01A."
		::= { upsApm160snmpEntry 671 }
upsApm160snmp_672_Branch34Energy OBJECT-TYPE
		SYNTAX Integer32
		
		MAX-ACCESS read-only
		STATUS current
		DESCRIPTION
		"upsApm160snmp_672_Branch34Energy stored as 0.01kWh."
		::= { upsApm160snmpEntry 672 }
upsApm160snmp_673_Branch34SwitchStatus OBJECT-TYPE
		SYNTAX INTEGER {
			open(0),
			close(1) }
		MAX-ACCESS read-only
		STATUS current
		DESCRIPTION
		"upsApm160snmp_673_Branch34SwitchStatus status."
		::= { upsApm160snmpEntry 673 }
upsApm160snmp_674_Branch34ActivePower OBJECT-TYPE
		SYNTAX Integer32
		
		MAX-ACCESS read-only
		STATUS current
		DESCRIPTION
		"upsApm160snmp_674_Branch34ActivePower stored as 0.01kW."
		::= { upsApm160snmpEntry 674 }
upsApm160snmp_675_Branch34ApparentPower OBJECT-TYPE
		SYNTAX Integer32
		
		MAX-ACCESS read-only
		STATUS current
		DESCRIPTION
		"upsApm160snmp_675_Branch34ApparentPower stored as 0.01kVA."
		::= { upsApm160snmpEntry 675 }
upsApm160snmp_676_Branch34THDi OBJECT-TYPE
		SYNTAX Integer32
		
		MAX-ACCESS read-only
		STATUS current
		DESCRIPTION
		"upsApm160snmp_676_Branch34THDi stored as 0.01%."
		::= { upsApm160snmpEntry 676 }
upsApm160snmp_677_Branch34RatedCurrent OBJECT-TYPE
		SYNTAX Integer32
		
		MAX-ACCESS read-only
		STATUS current
		DESCRIPTION
		"upsApm160snmp_677_Branch34RatedCurrent stored as 0.01A."
		::= { upsApm160snmpEntry 677 }
upsApm160snmp_678_Branch34LoadRatio OBJECT-TYPE
		SYNTAX Integer32
		
		MAX-ACCESS read-only
		STATUS current
		DESCRIPTION
		"upsApm160snmp_678_Branch34LoadRatio stored as 0.01%."
		::= { upsApm160snmpEntry 678 }
upsApm160snmp_679_Branch34PowerFactor OBJECT-TYPE
		SYNTAX Integer32
		
		MAX-ACCESS read-only
		STATUS current
		DESCRIPTION
		"upsApm160snmp_679_Branch34PowerFactor stored as 0.01."
		::= { upsApm160snmpEntry 679 }
upsApm160snmp_680_Branch34Voltage OBJECT-TYPE
		SYNTAX Integer32
		
		MAX-ACCESS read-only
		STATUS current
		DESCRIPTION
		"upsApm160snmp_680_Branch34Voltage stored as 0.01V."
		::= { upsApm160snmpEntry 680 }
upsApm160snmp_681_Branch35Current OBJECT-TYPE
		SYNTAX Integer32
		
		MAX-ACCESS read-only
		STATUS current
		DESCRIPTION
		"upsApm160snmp_681_Branch35Current stored as 0.01A."
		::= { upsApm160snmpEntry 681 }
upsApm160snmp_682_Branch35Energy OBJECT-TYPE
		SYNTAX Integer32
		
		MAX-ACCESS read-only
		STATUS current
		DESCRIPTION
		"upsApm160snmp_682_Branch35Energy stored as 0.01kWh."
		::= { upsApm160snmpEntry 682 }
upsApm160snmp_683_Branch35SwitchStatus OBJECT-TYPE
		SYNTAX INTEGER {
			open(0),
			close(1) }
		MAX-ACCESS read-only
		STATUS current
		DESCRIPTION
		"upsApm160snmp_683_Branch35SwitchStatus status."
		::= { upsApm160snmpEntry 683 }
upsApm160snmp_684_Branch35ActivePower OBJECT-TYPE
		SYNTAX Integer32
		
		MAX-ACCESS read-only
		STATUS current
		DESCRIPTION
		"upsApm160snmp_684_Branch35ActivePower stored as 0.01kW."
		::= { upsApm160snmpEntry 684 }
upsApm160snmp_685_Branch35ApparentPower OBJECT-TYPE
		SYNTAX Integer32
		
		MAX-ACCESS read-only
		STATUS current
		DESCRIPTION
		"upsApm160snmp_685_Branch35ApparentPower stored as 0.01kVA."
		::= { upsApm160snmpEntry 685 }
upsApm160snmp_686_Branch35THDi OBJECT-TYPE
		SYNTAX Integer32
		
		MAX-ACCESS read-only
		STATUS current
		DESCRIPTION
		"upsApm160snmp_686_Branch35THDi stored as 0.01%."
		::= { upsApm160snmpEntry 686 }
upsApm160snmp_687_Branch35RatedCurrent OBJECT-TYPE
		SYNTAX Integer32
		
		MAX-ACCESS read-only
		STATUS current
		DESCRIPTION
		"upsApm160snmp_687_Branch35RatedCurrent stored as 0.01A."
		::= { upsApm160snmpEntry 687 }
upsApm160snmp_688_Branch35LoadRatio OBJECT-TYPE
		SYNTAX Integer32
		
		MAX-ACCESS read-only
		STATUS current
		DESCRIPTION
		"upsApm160snmp_688_Branch35LoadRatio stored as 0.01%."
		::= { upsApm160snmpEntry 688 }
upsApm160snmp_689_Branch35PowerFactor OBJECT-TYPE
		SYNTAX Integer32
		
		MAX-ACCESS read-only
		STATUS current
		DESCRIPTION
		"upsApm160snmp_689_Branch35PowerFactor stored as 0.01."
		::= { upsApm160snmpEntry 689 }
upsApm160snmp_690_Branch35Voltage OBJECT-TYPE
		SYNTAX Integer32
		
		MAX-ACCESS read-only
		STATUS current
		DESCRIPTION
		"upsApm160snmp_690_Branch35Voltage stored as 0.01V."
		::= { upsApm160snmpEntry 690 }
upsApm160snmp_691_Branch36Current OBJECT-TYPE
		SYNTAX Integer32
		
		MAX-ACCESS read-only
		STATUS current
		DESCRIPTION
		"upsApm160snmp_691_Branch36Current stored as 0.01A."
		::= { upsApm160snmpEntry 691 }
upsApm160snmp_692_Branch36Energy OBJECT-TYPE
		SYNTAX Integer32
		
		MAX-ACCESS read-only
		STATUS current
		DESCRIPTION
		"upsApm160snmp_692_Branch36Energy stored as 0.01kWh."
		::= { upsApm160snmpEntry 692 }
upsApm160snmp_693_Branch36SwitchStatus OBJECT-TYPE
		SYNTAX INTEGER {
			open(0),
			close(1) }
		MAX-ACCESS read-only
		STATUS current
		DESCRIPTION
		"upsApm160snmp_693_Branch36SwitchStatus status."
		::= { upsApm160snmpEntry 693 }
upsApm160snmp_694_Branch36ActivePower OBJECT-TYPE
		SYNTAX Integer32
		
		MAX-ACCESS read-only
		STATUS current
		DESCRIPTION
		"upsApm160snmp_694_Branch36ActivePower stored as 0.01kW."
		::= { upsApm160snmpEntry 694 }
upsApm160snmp_695_Branch36ApparentPower OBJECT-TYPE
		SYNTAX Integer32
		
		MAX-ACCESS read-only
		STATUS current
		DESCRIPTION
		"upsApm160snmp_695_Branch36ApparentPower stored as 0.01kVA."
		::= { upsApm160snmpEntry 695 }
upsApm160snmp_696_Branch36THDi OBJECT-TYPE
		SYNTAX Integer32
		
		MAX-ACCESS read-only
		STATUS current
		DESCRIPTION
		"upsApm160snmp_696_Branch36THDi stored as 0.01%."
		::= { upsApm160snmpEntry 696 }
upsApm160snmp_697_Branch36RatedCurrent OBJECT-TYPE
		SYNTAX Integer32
		
		MAX-ACCESS read-only
		STATUS current
		DESCRIPTION
		"upsApm160snmp_697_Branch36RatedCurrent stored as 0.01A."
		::= { upsApm160snmpEntry 697 }
upsApm160snmp_698_Branch36LoadRatio OBJECT-TYPE
		SYNTAX Integer32
		
		MAX-ACCESS read-only
		STATUS current
		DESCRIPTION
		"upsApm160snmp_698_Branch36LoadRatio stored as 0.01%."
		::= { upsApm160snmpEntry 698 }
upsApm160snmp_699_Branch36PowerFactor OBJECT-TYPE
		SYNTAX Integer32
		
		MAX-ACCESS read-only
		STATUS current
		DESCRIPTION
		"upsApm160snmp_699_Branch36PowerFactor stored as 0.01."
		::= { upsApm160snmpEntry 699 }
upsApm160snmp_700_Branch36Voltage OBJECT-TYPE
		SYNTAX Integer32
		
		MAX-ACCESS read-only
		STATUS current
		DESCRIPTION
		"upsApm160snmp_700_Branch36Voltage stored as 0.01V."
		::= { upsApm160snmpEntry 700 }
upsApm160snmp_701_Branch37Current OBJECT-TYPE
		SYNTAX Integer32
		
		MAX-ACCESS read-only
		STATUS current
		DESCRIPTION
		"upsApm160snmp_701_Branch37Current stored as 0.01A."
		::= { upsApm160snmpEntry 701 }
upsApm160snmp_702_Branch37Energy OBJECT-TYPE
		SYNTAX Integer32
		
		MAX-ACCESS read-only
		STATUS current
		DESCRIPTION
		"upsApm160snmp_702_Branch37Energy stored as 0.01kWh."
		::= { upsApm160snmpEntry 702 }
upsApm160snmp_703_Branch37SwitchStatus OBJECT-TYPE
		SYNTAX INTEGER {
			open(0),
			close(1) }
		MAX-ACCESS read-only
		STATUS current
		DESCRIPTION
		"upsApm160snmp_703_Branch37SwitchStatus status."
		::= { upsApm160snmpEntry 703 }
upsApm160snmp_704_Branch37ActivePower OBJECT-TYPE
		SYNTAX Integer32
		
		MAX-ACCESS read-only
		STATUS current
		DESCRIPTION
		"upsApm160snmp_704_Branch37ActivePower stored as 0.01kW."
		::= { upsApm160snmpEntry 704 }
upsApm160snmp_705_Branch37ApparentPower OBJECT-TYPE
		SYNTAX Integer32
		
		MAX-ACCESS read-only
		STATUS current
		DESCRIPTION
		"upsApm160snmp_705_Branch37ApparentPower stored as 0.01kVA."
		::= { upsApm160snmpEntry 705 }
upsApm160snmp_706_Branch37THDi OBJECT-TYPE
		SYNTAX Integer32
		
		MAX-ACCESS read-only
		STATUS current
		DESCRIPTION
		"upsApm160snmp_706_Branch37THDi stored as 0.01%."
		::= { upsApm160snmpEntry 706 }
upsApm160snmp_707_Branch37RatedCurrent OBJECT-TYPE
		SYNTAX Integer32
		
		MAX-ACCESS read-only
		STATUS current
		DESCRIPTION
		"upsApm160snmp_707_Branch37RatedCurrent stored as 0.01A."
		::= { upsApm160snmpEntry 707 }
upsApm160snmp_708_Branch37LoadRatio OBJECT-TYPE
		SYNTAX Integer32
		
		MAX-ACCESS read-only
		STATUS current
		DESCRIPTION
		"upsApm160snmp_708_Branch37LoadRatio stored as 0.01%."
		::= { upsApm160snmpEntry 708 }
upsApm160snmp_709_Branch37PowerFactor OBJECT-TYPE
		SYNTAX Integer32
		
		MAX-ACCESS read-only
		STATUS current
		DESCRIPTION
		"upsApm160snmp_709_Branch37PowerFactor stored as 0.01."
		::= { upsApm160snmpEntry 709 }
upsApm160snmp_710_Branch37Voltage OBJECT-TYPE
		SYNTAX Integer32
		
		MAX-ACCESS read-only
		STATUS current
		DESCRIPTION
		"upsApm160snmp_710_Branch37Voltage stored as 0.01V."
		::= { upsApm160snmpEntry 710 }
upsApm160snmp_711_Branch38Current OBJECT-TYPE
		SYNTAX Integer32
		
		MAX-ACCESS read-only
		STATUS current
		DESCRIPTION
		"upsApm160snmp_711_Branch38Current stored as 0.01A."
		::= { upsApm160snmpEntry 711 }
upsApm160snmp_712_Branch38Energy OBJECT-TYPE
		SYNTAX Integer32
		
		MAX-ACCESS read-only
		STATUS current
		DESCRIPTION
		"upsApm160snmp_712_Branch38Energy stored as 0.01kWh."
		::= { upsApm160snmpEntry 712 }
upsApm160snmp_713_Branch38SwitchStatus OBJECT-TYPE
		SYNTAX INTEGER {
			open(0),
			close(1) }
		MAX-ACCESS read-only
		STATUS current
		DESCRIPTION
		"upsApm160snmp_713_Branch38SwitchStatus status."
		::= { upsApm160snmpEntry 713 }
upsApm160snmp_714_Branch38ActivePower OBJECT-TYPE
		SYNTAX Integer32
		
		MAX-ACCESS read-only
		STATUS current
		DESCRIPTION
		"upsApm160snmp_714_Branch38ActivePower stored as 0.01kW."
		::= { upsApm160snmpEntry 714 }
upsApm160snmp_715_Branch38ApparentPower OBJECT-TYPE
		SYNTAX Integer32
		
		MAX-ACCESS read-only
		STATUS current
		DESCRIPTION
		"upsApm160snmp_715_Branch38ApparentPower stored as 0.01kVA."
		::= { upsApm160snmpEntry 715 }
upsApm160snmp_716_Branch38THDi OBJECT-TYPE
		SYNTAX Integer32
		
		MAX-ACCESS read-only
		STATUS current
		DESCRIPTION
		"upsApm160snmp_716_Branch38THDi stored as 0.01%."
		::= { upsApm160snmpEntry 716 }
upsApm160snmp_717_Branch38RatedCurrent OBJECT-TYPE
		SYNTAX Integer32
		
		MAX-ACCESS read-only
		STATUS current
		DESCRIPTION
		"upsApm160snmp_717_Branch38RatedCurrent stored as 0.01A."
		::= { upsApm160snmpEntry 717 }
upsApm160snmp_718_Branch38LoadRatio OBJECT-TYPE
		SYNTAX Integer32
		
		MAX-ACCESS read-only
		STATUS current
		DESCRIPTION
		"upsApm160snmp_718_Branch38LoadRatio stored as 0.01%."
		::= { upsApm160snmpEntry 718 }
upsApm160snmp_719_Branch38PowerFactor OBJECT-TYPE
		SYNTAX Integer32
		
		MAX-ACCESS read-only
		STATUS current
		DESCRIPTION
		"upsApm160snmp_719_Branch38PowerFactor stored as 0.01."
		::= { upsApm160snmpEntry 719 }
upsApm160snmp_720_Branch38Voltage OBJECT-TYPE
		SYNTAX Integer32
		
		MAX-ACCESS read-only
		STATUS current
		DESCRIPTION
		"upsApm160snmp_720_Branch38Voltage stored as 0.01V."
		::= { upsApm160snmpEntry 720 }
upsApm160snmp_721_Branch39Current OBJECT-TYPE
		SYNTAX Integer32
		
		MAX-ACCESS read-only
		STATUS current
		DESCRIPTION
		"upsApm160snmp_721_Branch39Current stored as 0.01A."
		::= { upsApm160snmpEntry 721 }
upsApm160snmp_722_Branch39Energy OBJECT-TYPE
		SYNTAX Integer32
		
		MAX-ACCESS read-only
		STATUS current
		DESCRIPTION
		"upsApm160snmp_722_Branch39Energy stored as 0.01kWh."
		::= { upsApm160snmpEntry 722 }
upsApm160snmp_723_Branch39SwitchStatus OBJECT-TYPE
		SYNTAX INTEGER {
			open(0),
			close(1) }
		MAX-ACCESS read-only
		STATUS current
		DESCRIPTION
		"upsApm160snmp_723_Branch39SwitchStatus status."
		::= { upsApm160snmpEntry 723 }
upsApm160snmp_724_Branch39ActivePower OBJECT-TYPE
		SYNTAX Integer32
		
		MAX-ACCESS read-only
		STATUS current
		DESCRIPTION
		"upsApm160snmp_724_Branch39ActivePower stored as 0.01kW."
		::= { upsApm160snmpEntry 724 }
upsApm160snmp_725_Branch39ApparentPower OBJECT-TYPE
		SYNTAX Integer32
		
		MAX-ACCESS read-only
		STATUS current
		DESCRIPTION
		"upsApm160snmp_725_Branch39ApparentPower stored as 0.01kVA."
		::= { upsApm160snmpEntry 725 }
upsApm160snmp_726_Branch39THDi OBJECT-TYPE
		SYNTAX Integer32
		
		MAX-ACCESS read-only
		STATUS current
		DESCRIPTION
		"upsApm160snmp_726_Branch39THDi stored as 0.01%."
		::= { upsApm160snmpEntry 726 }
upsApm160snmp_727_Branch39RatedCurrent OBJECT-TYPE
		SYNTAX Integer32
		
		MAX-ACCESS read-only
		STATUS current
		DESCRIPTION
		"upsApm160snmp_727_Branch39RatedCurrent stored as 0.01A."
		::= { upsApm160snmpEntry 727 }
upsApm160snmp_728_Branch39LoadRatio OBJECT-TYPE
		SYNTAX Integer32
		
		MAX-ACCESS read-only
		STATUS current
		DESCRIPTION
		"upsApm160snmp_728_Branch39LoadRatio stored as 0.01%."
		::= { upsApm160snmpEntry 728 }
upsApm160snmp_729_Branch39PowerFactor OBJECT-TYPE
		SYNTAX Integer32
		
		MAX-ACCESS read-only
		STATUS current
		DESCRIPTION
		"upsApm160snmp_729_Branch39PowerFactor stored as 0.01."
		::= { upsApm160snmpEntry 729 }
upsApm160snmp_730_Branch39Voltage OBJECT-TYPE
		SYNTAX Integer32
		
		MAX-ACCESS read-only
		STATUS current
		DESCRIPTION
		"upsApm160snmp_730_Branch39Voltage stored as 0.01V."
		::= { upsApm160snmpEntry 730 }
upsApm160snmp_731_Branch40Current OBJECT-TYPE
		SYNTAX Integer32
		
		MAX-ACCESS read-only
		STATUS current
		DESCRIPTION
		"upsApm160snmp_731_Branch40Current stored as 0.01A."
		::= { upsApm160snmpEntry 731 }
upsApm160snmp_732_Branch40Energy OBJECT-TYPE
		SYNTAX Integer32
		
		MAX-ACCESS read-only
		STATUS current
		DESCRIPTION
		"upsApm160snmp_732_Branch40Energy stored as 0.01kWh."
		::= { upsApm160snmpEntry 732 }
upsApm160snmp_733_Branch40SwitchStatus OBJECT-TYPE
		SYNTAX INTEGER {
			open(0),
			close(1) }
		MAX-ACCESS read-only
		STATUS current
		DESCRIPTION
		"upsApm160snmp_733_Branch40SwitchStatus status."
		::= { upsApm160snmpEntry 733 }
upsApm160snmp_734_Branch40ActivePower OBJECT-TYPE
		SYNTAX Integer32
		
		MAX-ACCESS read-only
		STATUS current
		DESCRIPTION
		"upsApm160snmp_734_Branch40ActivePower stored as 0.01kW."
		::= { upsApm160snmpEntry 734 }
upsApm160snmp_735_Branch40ApparentPower OBJECT-TYPE
		SYNTAX Integer32
		
		MAX-ACCESS read-only
		STATUS current
		DESCRIPTION
		"upsApm160snmp_735_Branch40ApparentPower stored as 0.01kVA."
		::= { upsApm160snmpEntry 735 }
upsApm160snmp_736_Branch40THDi OBJECT-TYPE
		SYNTAX Integer32
		
		MAX-ACCESS read-only
		STATUS current
		DESCRIPTION
		"upsApm160snmp_736_Branch40THDi stored as 0.01%."
		::= { upsApm160snmpEntry 736 }
upsApm160snmp_737_Branch40RatedCurrent OBJECT-TYPE
		SYNTAX Integer32
		
		MAX-ACCESS read-only
		STATUS current
		DESCRIPTION
		"upsApm160snmp_737_Branch40RatedCurrent stored as 0.01A."
		::= { upsApm160snmpEntry 737 }
upsApm160snmp_738_Branch40LoadRatio OBJECT-TYPE
		SYNTAX Integer32
		
		MAX-ACCESS read-only
		STATUS current
		DESCRIPTION
		"upsApm160snmp_738_Branch40LoadRatio stored as 0.01%."
		::= { upsApm160snmpEntry 738 }
upsApm160snmp_739_Branch40PowerFactor OBJECT-TYPE
		SYNTAX Integer32
		
		MAX-ACCESS read-only
		STATUS current
		DESCRIPTION
		"upsApm160snmp_739_Branch40PowerFactor stored as 0.01."
		::= { upsApm160snmpEntry 739 }
upsApm160snmp_740_Branch40Voltage OBJECT-TYPE
		SYNTAX Integer32
		
		MAX-ACCESS read-only
		STATUS current
		DESCRIPTION
		"upsApm160snmp_740_Branch40Voltage stored as 0.01V."
		::= { upsApm160snmpEntry 740 }
upsApm160snmp_741_Branch41Current OBJECT-TYPE
		SYNTAX Integer32
		
		MAX-ACCESS read-only
		STATUS current
		DESCRIPTION
		"upsApm160snmp_741_Branch41Current stored as 0.01A."
		::= { upsApm160snmpEntry 741 }
upsApm160snmp_742_Branch41Energy OBJECT-TYPE
		SYNTAX Integer32
		
		MAX-ACCESS read-only
		STATUS current
		DESCRIPTION
		"upsApm160snmp_742_Branch41Energy stored as 0.01kWh."
		::= { upsApm160snmpEntry 742 }
upsApm160snmp_743_Branch41SwitchStatus OBJECT-TYPE
		SYNTAX INTEGER {
			open(0),
			close(1) }
		MAX-ACCESS read-only
		STATUS current
		DESCRIPTION
		"upsApm160snmp_743_Branch41SwitchStatus status."
		::= { upsApm160snmpEntry 743 }
upsApm160snmp_744_Branch41ActivePower OBJECT-TYPE
		SYNTAX Integer32
		
		MAX-ACCESS read-only
		STATUS current
		DESCRIPTION
		"upsApm160snmp_744_Branch41ActivePower stored as 0.01kW."
		::= { upsApm160snmpEntry 744 }
upsApm160snmp_745_Branch41ApparentPower OBJECT-TYPE
		SYNTAX Integer32
		
		MAX-ACCESS read-only
		STATUS current
		DESCRIPTION
		"upsApm160snmp_745_Branch41ApparentPower stored as 0.01kVA."
		::= { upsApm160snmpEntry 745 }
upsApm160snmp_746_Branch41THDi OBJECT-TYPE
		SYNTAX Integer32
		
		MAX-ACCESS read-only
		STATUS current
		DESCRIPTION
		"upsApm160snmp_746_Branch41THDi stored as 0.01%."
		::= { upsApm160snmpEntry 746 }
upsApm160snmp_747_Branch41RatedCurrent OBJECT-TYPE
		SYNTAX Integer32
		
		MAX-ACCESS read-only
		STATUS current
		DESCRIPTION
		"upsApm160snmp_747_Branch41RatedCurrent stored as 0.01A."
		::= { upsApm160snmpEntry 747 }
upsApm160snmp_748_Branch41LoadRatio OBJECT-TYPE
		SYNTAX Integer32
		
		MAX-ACCESS read-only
		STATUS current
		DESCRIPTION
		"upsApm160snmp_748_Branch41LoadRatio stored as 0.01%."
		::= { upsApm160snmpEntry 748 }
upsApm160snmp_749_Branch41PowerFactor OBJECT-TYPE
		SYNTAX Integer32
		
		MAX-ACCESS read-only
		STATUS current
		DESCRIPTION
		"upsApm160snmp_749_Branch41PowerFactor stored as 0.01."
		::= { upsApm160snmpEntry 749 }
upsApm160snmp_750_Branch41Voltage OBJECT-TYPE
		SYNTAX Integer32
		
		MAX-ACCESS read-only
		STATUS current
		DESCRIPTION
		"upsApm160snmp_750_Branch41Voltage stored as 0.01V."
		::= { upsApm160snmpEntry 750 }
upsApm160snmp_751_Branch42Current OBJECT-TYPE
		SYNTAX Integer32
		
		MAX-ACCESS read-only
		STATUS current
		DESCRIPTION
		"upsApm160snmp_751_Branch42Current stored as 0.01A."
		::= { upsApm160snmpEntry 751 }
upsApm160snmp_752_Branch42Energy OBJECT-TYPE
		SYNTAX Integer32
		
		MAX-ACCESS read-only
		STATUS current
		DESCRIPTION
		"upsApm160snmp_752_Branch42Energy stored as 0.01kWh."
		::= { upsApm160snmpEntry 752 }
upsApm160snmp_753_Branch42SwitchStatus OBJECT-TYPE
		SYNTAX INTEGER {
			open(0),
			close(1) }
		MAX-ACCESS read-only
		STATUS current
		DESCRIPTION
		"upsApm160snmp_753_Branch42SwitchStatus status."
		::= { upsApm160snmpEntry 753 }
upsApm160snmp_754_Branch42ActivePower OBJECT-TYPE
		SYNTAX Integer32
		
		MAX-ACCESS read-only
		STATUS current
		DESCRIPTION
		"upsApm160snmp_754_Branch42ActivePower stored as 0.01kW."
		::= { upsApm160snmpEntry 754 }
upsApm160snmp_755_Branch42ApparentPower OBJECT-TYPE
		SYNTAX Integer32
		
		MAX-ACCESS read-only
		STATUS current
		DESCRIPTION
		"upsApm160snmp_755_Branch42ApparentPower stored as 0.01kVA."
		::= { upsApm160snmpEntry 755 }
upsApm160snmp_756_Branch42THDi OBJECT-TYPE
		SYNTAX Integer32
		
		MAX-ACCESS read-only
		STATUS current
		DESCRIPTION
		"upsApm160snmp_756_Branch42THDi stored as 0.01%."
		::= { upsApm160snmpEntry 756 }
upsApm160snmp_757_Branch42RatedCurrent OBJECT-TYPE
		SYNTAX Integer32
		
		MAX-ACCESS read-only
		STATUS current
		DESCRIPTION
		"upsApm160snmp_757_Branch42RatedCurrent stored as 0.01A."
		::= { upsApm160snmpEntry 757 }
upsApm160snmp_758_Branch42LoadRatio OBJECT-TYPE
		SYNTAX Integer32
		
		MAX-ACCESS read-only
		STATUS current
		DESCRIPTION
		"upsApm160snmp_758_Branch42LoadRatio stored as 0.01%."
		::= { upsApm160snmpEntry 758 }
upsApm160snmp_759_Branch42PowerFactor OBJECT-TYPE
		SYNTAX Integer32
		
		MAX-ACCESS read-only
		STATUS current
		DESCRIPTION
		"upsApm160snmp_759_Branch42PowerFactor stored as 0.01."
		::= { upsApm160snmpEntry 759 }
upsApm160snmp_760_Branch42Voltage OBJECT-TYPE
		SYNTAX Integer32
		
		MAX-ACCESS read-only
		STATUS current
		DESCRIPTION
		"upsApm160snmp_760_Branch42Voltage stored as 0.01V."
		::= { upsApm160snmpEntry 760 }
upsApm160snmp_761_Branch43Current OBJECT-TYPE
		SYNTAX Integer32
		
		MAX-ACCESS read-only
		STATUS current
		DESCRIPTION
		"upsApm160snmp_761_Branch43Current stored as 0.01A."
		::= { upsApm160snmpEntry 761 }
upsApm160snmp_762_Branch43Energy OBJECT-TYPE
		SYNTAX Integer32
		
		MAX-ACCESS read-only
		STATUS current
		DESCRIPTION
		"upsApm160snmp_762_Branch43Energy stored as 0.01kWh."
		::= { upsApm160snmpEntry 762 }
upsApm160snmp_763_Branch43SwitchStatus OBJECT-TYPE
		SYNTAX INTEGER {
			open(0),
			close(1) }
		MAX-ACCESS read-only
		STATUS current
		DESCRIPTION
		"upsApm160snmp_763_Branch43SwitchStatus status."
		::= { upsApm160snmpEntry 763 }
upsApm160snmp_764_Branch43ActivePower OBJECT-TYPE
		SYNTAX Integer32
		
		MAX-ACCESS read-only
		STATUS current
		DESCRIPTION
		"upsApm160snmp_764_Branch43ActivePower stored as 0.01kW."
		::= { upsApm160snmpEntry 764 }
upsApm160snmp_765_Branch43ApparentPower OBJECT-TYPE
		SYNTAX Integer32
		
		MAX-ACCESS read-only
		STATUS current
		DESCRIPTION
		"upsApm160snmp_765_Branch43ApparentPower stored as 0.01kVA."
		::= { upsApm160snmpEntry 765 }
upsApm160snmp_766_Branch43THDi OBJECT-TYPE
		SYNTAX Integer32
		
		MAX-ACCESS read-only
		STATUS current
		DESCRIPTION
		"upsApm160snmp_766_Branch43THDi stored as 0.01%."
		::= { upsApm160snmpEntry 766 }
upsApm160snmp_767_Branch43RatedCurrent OBJECT-TYPE
		SYNTAX Integer32
		
		MAX-ACCESS read-only
		STATUS current
		DESCRIPTION
		"upsApm160snmp_767_Branch43RatedCurrent stored as 0.01A."
		::= { upsApm160snmpEntry 767 }
upsApm160snmp_768_Branch43LoadRatio OBJECT-TYPE
		SYNTAX Integer32
		
		MAX-ACCESS read-only
		STATUS current
		DESCRIPTION
		"upsApm160snmp_768_Branch43LoadRatio stored as 0.01%."
		::= { upsApm160snmpEntry 768 }
upsApm160snmp_769_Branch43PowerFactor OBJECT-TYPE
		SYNTAX Integer32
		
		MAX-ACCESS read-only
		STATUS current
		DESCRIPTION
		"upsApm160snmp_769_Branch43PowerFactor stored as 0.01."
		::= { upsApm160snmpEntry 769 }
upsApm160snmp_770_Branch43Voltage OBJECT-TYPE
		SYNTAX Integer32
		
		MAX-ACCESS read-only
		STATUS current
		DESCRIPTION
		"upsApm160snmp_770_Branch43Voltage stored as 0.01V."
		::= { upsApm160snmpEntry 770 }
upsApm160snmp_771_Branch44Current OBJECT-TYPE
		SYNTAX Integer32
		
		MAX-ACCESS read-only
		STATUS current
		DESCRIPTION
		"upsApm160snmp_771_Branch44Current stored as 0.01A."
		::= { upsApm160snmpEntry 771 }
upsApm160snmp_772_Branch44Energy OBJECT-TYPE
		SYNTAX Integer32
		
		MAX-ACCESS read-only
		STATUS current
		DESCRIPTION
		"upsApm160snmp_772_Branch44Energy stored as 0.01kWh."
		::= { upsApm160snmpEntry 772 }
upsApm160snmp_773_Branch44SwitchStatus OBJECT-TYPE
		SYNTAX INTEGER {
			open(0),
			close(1) }
		MAX-ACCESS read-only
		STATUS current
		DESCRIPTION
		"upsApm160snmp_773_Branch44SwitchStatus status."
		::= { upsApm160snmpEntry 773 }
upsApm160snmp_774_Branch44ActivePower OBJECT-TYPE
		SYNTAX Integer32
		
		MAX-ACCESS read-only
		STATUS current
		DESCRIPTION
		"upsApm160snmp_774_Branch44ActivePower stored as 0.01kW."
		::= { upsApm160snmpEntry 774 }
upsApm160snmp_775_Branch44ApparentPower OBJECT-TYPE
		SYNTAX Integer32
		
		MAX-ACCESS read-only
		STATUS current
		DESCRIPTION
		"upsApm160snmp_775_Branch44ApparentPower stored as 0.01kVA."
		::= { upsApm160snmpEntry 775 }
upsApm160snmp_776_Branch44THDi OBJECT-TYPE
		SYNTAX Integer32
		
		MAX-ACCESS read-only
		STATUS current
		DESCRIPTION
		"upsApm160snmp_776_Branch44THDi stored as 0.01%."
		::= { upsApm160snmpEntry 776 }
upsApm160snmp_777_Branch44RatedCurrent OBJECT-TYPE
		SYNTAX Integer32
		
		MAX-ACCESS read-only
		STATUS current
		DESCRIPTION
		"upsApm160snmp_777_Branch44RatedCurrent stored as 0.01A."
		::= { upsApm160snmpEntry 777 }
upsApm160snmp_778_Branch44LoadRatio OBJECT-TYPE
		SYNTAX Integer32
		
		MAX-ACCESS read-only
		STATUS current
		DESCRIPTION
		"upsApm160snmp_778_Branch44LoadRatio stored as 0.01%."
		::= { upsApm160snmpEntry 778 }
upsApm160snmp_779_Branch44PowerFactor OBJECT-TYPE
		SYNTAX Integer32
		
		MAX-ACCESS read-only
		STATUS current
		DESCRIPTION
		"upsApm160snmp_779_Branch44PowerFactor stored as 0.01."
		::= { upsApm160snmpEntry 779 }
upsApm160snmp_780_Branch44Voltage OBJECT-TYPE
		SYNTAX Integer32
		
		MAX-ACCESS read-only
		STATUS current
		DESCRIPTION
		"upsApm160snmp_780_Branch44Voltage stored as 0.01V."
		::= { upsApm160snmpEntry 780 }
upsApm160snmp_781_Branch45Current OBJECT-TYPE
		SYNTAX Integer32
		
		MAX-ACCESS read-only
		STATUS current
		DESCRIPTION
		"upsApm160snmp_781_Branch45Current stored as 0.01A."
		::= { upsApm160snmpEntry 781 }
upsApm160snmp_782_Branch45Energy OBJECT-TYPE
		SYNTAX Integer32
		
		MAX-ACCESS read-only
		STATUS current
		DESCRIPTION
		"upsApm160snmp_782_Branch45Energy stored as 0.01kWh."
		::= { upsApm160snmpEntry 782 }
upsApm160snmp_783_Branch45SwitchStatus OBJECT-TYPE
		SYNTAX INTEGER {
			open(0),
			close(1) }
		MAX-ACCESS read-only
		STATUS current
		DESCRIPTION
		"upsApm160snmp_783_Branch45SwitchStatus status."
		::= { upsApm160snmpEntry 783 }
upsApm160snmp_784_Branch45ActivePower OBJECT-TYPE
		SYNTAX Integer32
		
		MAX-ACCESS read-only
		STATUS current
		DESCRIPTION
		"upsApm160snmp_784_Branch45ActivePower stored as 0.01kW."
		::= { upsApm160snmpEntry 784 }
upsApm160snmp_785_Branch45ApparentPower OBJECT-TYPE
		SYNTAX Integer32
		
		MAX-ACCESS read-only
		STATUS current
		DESCRIPTION
		"upsApm160snmp_785_Branch45ApparentPower stored as 0.01kVA."
		::= { upsApm160snmpEntry 785 }
upsApm160snmp_786_Branch45THDi OBJECT-TYPE
		SYNTAX Integer32
		
		MAX-ACCESS read-only
		STATUS current
		DESCRIPTION
		"upsApm160snmp_786_Branch45THDi stored as 0.01%."
		::= { upsApm160snmpEntry 786 }
upsApm160snmp_787_Branch45RatedCurrent OBJECT-TYPE
		SYNTAX Integer32
		
		MAX-ACCESS read-only
		STATUS current
		DESCRIPTION
		"upsApm160snmp_787_Branch45RatedCurrent stored as 0.01A."
		::= { upsApm160snmpEntry 787 }
upsApm160snmp_788_Branch45LoadRatio OBJECT-TYPE
		SYNTAX Integer32
		
		MAX-ACCESS read-only
		STATUS current
		DESCRIPTION
		"upsApm160snmp_788_Branch45LoadRatio stored as 0.01%."
		::= { upsApm160snmpEntry 788 }
upsApm160snmp_789_Branch45PowerFactor OBJECT-TYPE
		SYNTAX Integer32
		
		MAX-ACCESS read-only
		STATUS current
		DESCRIPTION
		"upsApm160snmp_789_Branch45PowerFactor stored as 0.01."
		::= { upsApm160snmpEntry 789 }
upsApm160snmp_790_Branch45Voltage OBJECT-TYPE
		SYNTAX Integer32
		
		MAX-ACCESS read-only
		STATUS current
		DESCRIPTION
		"upsApm160snmp_790_Branch45Voltage stored as 0.01V."
		::= { upsApm160snmpEntry 790 }
upsApm160snmp_791_Branch46Current OBJECT-TYPE
		SYNTAX Integer32
		
		MAX-ACCESS read-only
		STATUS current
		DESCRIPTION
		"upsApm160snmp_791_Branch46Current stored as 0.01A."
		::= { upsApm160snmpEntry 791 }
upsApm160snmp_792_Branch46Energy OBJECT-TYPE
		SYNTAX Integer32
		
		MAX-ACCESS read-only
		STATUS current
		DESCRIPTION
		"upsApm160snmp_792_Branch46Energy stored as 0.01kWh."
		::= { upsApm160snmpEntry 792 }
upsApm160snmp_793_Branch46SwitchStatus OBJECT-TYPE
		SYNTAX INTEGER {
			open(0),
			close(1) }
		MAX-ACCESS read-only
		STATUS current
		DESCRIPTION
		"upsApm160snmp_793_Branch46SwitchStatus status."
		::= { upsApm160snmpEntry 793 }
upsApm160snmp_794_Branch46ActivePower OBJECT-TYPE
		SYNTAX Integer32
		
		MAX-ACCESS read-only
		STATUS current
		DESCRIPTION
		"upsApm160snmp_794_Branch46ActivePower stored as 0.01kW."
		::= { upsApm160snmpEntry 794 }
upsApm160snmp_795_Branch46ApparentPower OBJECT-TYPE
		SYNTAX Integer32
		
		MAX-ACCESS read-only
		STATUS current
		DESCRIPTION
		"upsApm160snmp_795_Branch46ApparentPower stored as 0.01kVA."
		::= { upsApm160snmpEntry 795 }
upsApm160snmp_796_Branch46THDi OBJECT-TYPE
		SYNTAX Integer32
		
		MAX-ACCESS read-only
		STATUS current
		DESCRIPTION
		"upsApm160snmp_796_Branch46THDi stored as 0.01%."
		::= { upsApm160snmpEntry 796 }
upsApm160snmp_797_Branch46RatedCurrent OBJECT-TYPE
		SYNTAX Integer32
		
		MAX-ACCESS read-only
		STATUS current
		DESCRIPTION
		"upsApm160snmp_797_Branch46RatedCurrent stored as 0.01A."
		::= { upsApm160snmpEntry 797 }
upsApm160snmp_798_Branch46LoadRatio OBJECT-TYPE
		SYNTAX Integer32
		
		MAX-ACCESS read-only
		STATUS current
		DESCRIPTION
		"upsApm160snmp_798_Branch46LoadRatio stored as 0.01%."
		::= { upsApm160snmpEntry 798 }
upsApm160snmp_799_Branch46PowerFactor OBJECT-TYPE
		SYNTAX Integer32
		
		MAX-ACCESS read-only
		STATUS current
		DESCRIPTION
		"upsApm160snmp_799_Branch46PowerFactor stored as 0.01."
		::= { upsApm160snmpEntry 799 }
upsApm160snmp_800_Branch46Voltage OBJECT-TYPE
		SYNTAX Integer32
		
		MAX-ACCESS read-only
		STATUS current
		DESCRIPTION
		"upsApm160snmp_800_Branch46Voltage stored as 0.01V."
		::= { upsApm160snmpEntry 800 }
upsApm160snmp_801_Branch47Current OBJECT-TYPE
		SYNTAX Integer32
		
		MAX-ACCESS read-only
		STATUS current
		DESCRIPTION
		"upsApm160snmp_801_Branch47Current stored as 0.01A."
		::= { upsApm160snmpEntry 801 }
upsApm160snmp_802_Branch47Energy OBJECT-TYPE
		SYNTAX Integer32
		
		MAX-ACCESS read-only
		STATUS current
		DESCRIPTION
		"upsApm160snmp_802_Branch47Energy stored as 0.01kWh."
		::= { upsApm160snmpEntry 802 }
upsApm160snmp_803_Branch47SwitchStatus OBJECT-TYPE
		SYNTAX INTEGER {
			open(0),
			close(1) }
		MAX-ACCESS read-only
		STATUS current
		DESCRIPTION
		"upsApm160snmp_803_Branch47SwitchStatus status."
		::= { upsApm160snmpEntry 803 }
upsApm160snmp_804_Branch47ActivePower OBJECT-TYPE
		SYNTAX Integer32
		
		MAX-ACCESS read-only
		STATUS current
		DESCRIPTION
		"upsApm160snmp_804_Branch47ActivePower stored as 0.01kW."
		::= { upsApm160snmpEntry 804 }
upsApm160snmp_805_Branch47ApparentPower OBJECT-TYPE
		SYNTAX Integer32
		
		MAX-ACCESS read-only
		STATUS current
		DESCRIPTION
		"upsApm160snmp_805_Branch47ApparentPower stored as 0.01kVA."
		::= { upsApm160snmpEntry 805 }
upsApm160snmp_806_Branch47THDi OBJECT-TYPE
		SYNTAX Integer32
		
		MAX-ACCESS read-only
		STATUS current
		DESCRIPTION
		"upsApm160snmp_806_Branch47THDi stored as 0.01%."
		::= { upsApm160snmpEntry 806 }
upsApm160snmp_807_Branch47RatedCurrent OBJECT-TYPE
		SYNTAX Integer32
		
		MAX-ACCESS read-only
		STATUS current
		DESCRIPTION
		"upsApm160snmp_807_Branch47RatedCurrent stored as 0.01A."
		::= { upsApm160snmpEntry 807 }
upsApm160snmp_808_Branch47LoadRatio OBJECT-TYPE
		SYNTAX Integer32
		
		MAX-ACCESS read-only
		STATUS current
		DESCRIPTION
		"upsApm160snmp_808_Branch47LoadRatio stored as 0.01%."
		::= { upsApm160snmpEntry 808 }
upsApm160snmp_809_Branch47PowerFactor OBJECT-TYPE
		SYNTAX Integer32
		
		MAX-ACCESS read-only
		STATUS current
		DESCRIPTION
		"upsApm160snmp_809_Branch47PowerFactor stored as 0.01."
		::= { upsApm160snmpEntry 809 }
upsApm160snmp_810_Branch47Voltage OBJECT-TYPE
		SYNTAX Integer32
		
		MAX-ACCESS read-only
		STATUS current
		DESCRIPTION
		"upsApm160snmp_810_Branch47Voltage stored as 0.01V."
		::= { upsApm160snmpEntry 810 }
upsApm160snmp_811_Branch48Current OBJECT-TYPE
		SYNTAX Integer32
		
		MAX-ACCESS read-only
		STATUS current
		DESCRIPTION
		"upsApm160snmp_811_Branch48Current stored as 0.01A."
		::= { upsApm160snmpEntry 811 }
upsApm160snmp_812_Branch48Energy OBJECT-TYPE
		SYNTAX Integer32
		
		MAX-ACCESS read-only
		STATUS current
		DESCRIPTION
		"upsApm160snmp_812_Branch48Energy stored as 0.01kWh."
		::= { upsApm160snmpEntry 812 }
upsApm160snmp_813_Branch48SwitchStatus OBJECT-TYPE
		SYNTAX INTEGER {
			open(0),
			close(1) }
		MAX-ACCESS read-only
		STATUS current
		DESCRIPTION
		"upsApm160snmp_813_Branch48SwitchStatus status."
		::= { upsApm160snmpEntry 813 }
upsApm160snmp_814_Branch48ActivePower OBJECT-TYPE
		SYNTAX Integer32
		
		MAX-ACCESS read-only
		STATUS current
		DESCRIPTION
		"upsApm160snmp_814_Branch48ActivePower stored as 0.01kW."
		::= { upsApm160snmpEntry 814 }
upsApm160snmp_815_Branch48ApparentPower OBJECT-TYPE
		SYNTAX Integer32
		
		MAX-ACCESS read-only
		STATUS current
		DESCRIPTION
		"upsApm160snmp_815_Branch48ApparentPower stored as 0.01kVA."
		::= { upsApm160snmpEntry 815 }
upsApm160snmp_816_Branch48THDi OBJECT-TYPE
		SYNTAX Integer32
		
		MAX-ACCESS read-only
		STATUS current
		DESCRIPTION
		"upsApm160snmp_816_Branch48THDi stored as 0.01%."
		::= { upsApm160snmpEntry 816 }
upsApm160snmp_817_Branch48RatedCurrent OBJECT-TYPE
		SYNTAX Integer32
		
		MAX-ACCESS read-only
		STATUS current
		DESCRIPTION
		"upsApm160snmp_817_Branch48RatedCurrent stored as 0.01A."
		::= { upsApm160snmpEntry 817 }
upsApm160snmp_818_Branch48LoadRatio OBJECT-TYPE
		SYNTAX Integer32
		
		MAX-ACCESS read-only
		STATUS current
		DESCRIPTION
		"upsApm160snmp_818_Branch48LoadRatio stored as 0.01%."
		::= { upsApm160snmpEntry 818 }
upsApm160snmp_819_Branch48PowerFactor OBJECT-TYPE
		SYNTAX Integer32
		
		MAX-ACCESS read-only
		STATUS current
		DESCRIPTION
		"upsApm160snmp_819_Branch48PowerFactor stored as 0.01."
		::= { upsApm160snmpEntry 819 }
upsApm160snmp_820_Branch48Voltage OBJECT-TYPE
		SYNTAX Integer32
		
		MAX-ACCESS read-only
		STATUS current
		DESCRIPTION
		"upsApm160snmp_820_Branch48Voltage stored as 0.01V."
		::= { upsApm160snmpEntry 820 }
upsApm160snmp_821_Branch49Current OBJECT-TYPE
		SYNTAX Integer32
		
		MAX-ACCESS read-only
		STATUS current
		DESCRIPTION
		"upsApm160snmp_821_Branch49Current stored as 0.01A."
		::= { upsApm160snmpEntry 821 }
upsApm160snmp_822_Branch49Energy OBJECT-TYPE
		SYNTAX Integer32
		
		MAX-ACCESS read-only
		STATUS current
		DESCRIPTION
		"upsApm160snmp_822_Branch49Energy stored as 0.01kWh."
		::= { upsApm160snmpEntry 822 }
upsApm160snmp_823_Branch49SwitchStatus OBJECT-TYPE
		SYNTAX INTEGER {
			open(0),
			close(1) }
		MAX-ACCESS read-only
		STATUS current
		DESCRIPTION
		"upsApm160snmp_823_Branch49SwitchStatus status."
		::= { upsApm160snmpEntry 823 }
upsApm160snmp_824_Branch49ActivePower OBJECT-TYPE
		SYNTAX Integer32
		
		MAX-ACCESS read-only
		STATUS current
		DESCRIPTION
		"upsApm160snmp_824_Branch49ActivePower stored as 0.01kW."
		::= { upsApm160snmpEntry 824 }
upsApm160snmp_825_Branch49ApparentPower OBJECT-TYPE
		SYNTAX Integer32
		
		MAX-ACCESS read-only
		STATUS current
		DESCRIPTION
		"upsApm160snmp_825_Branch49ApparentPower stored as 0.01kVA."
		::= { upsApm160snmpEntry 825 }
upsApm160snmp_826_Branch49THDi OBJECT-TYPE
		SYNTAX Integer32
		
		MAX-ACCESS read-only
		STATUS current
		DESCRIPTION
		"upsApm160snmp_826_Branch49THDi stored as 0.01%."
		::= { upsApm160snmpEntry 826 }
upsApm160snmp_827_Branch49RatedCurrent OBJECT-TYPE
		SYNTAX Integer32
		
		MAX-ACCESS read-only
		STATUS current
		DESCRIPTION
		"upsApm160snmp_827_Branch49RatedCurrent stored as 0.01A."
		::= { upsApm160snmpEntry 827 }
upsApm160snmp_828_Branch49LoadRatio OBJECT-TYPE
		SYNTAX Integer32
		
		MAX-ACCESS read-only
		STATUS current
		DESCRIPTION
		"upsApm160snmp_828_Branch49LoadRatio stored as 0.01%."
		::= { upsApm160snmpEntry 828 }
upsApm160snmp_829_Branch49PowerFactor OBJECT-TYPE
		SYNTAX Integer32
		
		MAX-ACCESS read-only
		STATUS current
		DESCRIPTION
		"upsApm160snmp_829_Branch49PowerFactor stored as 0.01."
		::= { upsApm160snmpEntry 829 }
upsApm160snmp_830_Branch49Voltage OBJECT-TYPE
		SYNTAX Integer32
		
		MAX-ACCESS read-only
		STATUS current
		DESCRIPTION
		"upsApm160snmp_830_Branch49Voltage stored as 0.01V."
		::= { upsApm160snmpEntry 830 }
upsApm160snmp_831_Branch50Current OBJECT-TYPE
		SYNTAX Integer32
		
		MAX-ACCESS read-only
		STATUS current
		DESCRIPTION
		"upsApm160snmp_831_Branch50Current stored as 0.01A."
		::= { upsApm160snmpEntry 831 }
upsApm160snmp_832_Branch50Energy OBJECT-TYPE
		SYNTAX Integer32
		
		MAX-ACCESS read-only
		STATUS current
		DESCRIPTION
		"upsApm160snmp_832_Branch50Energy stored as 0.01kWh."
		::= { upsApm160snmpEntry 832 }
upsApm160snmp_833_Branch50SwitchStatus OBJECT-TYPE
		SYNTAX INTEGER {
			open(0),
			close(1) }
		MAX-ACCESS read-only
		STATUS current
		DESCRIPTION
		"upsApm160snmp_833_Branch50SwitchStatus status."
		::= { upsApm160snmpEntry 833 }
upsApm160snmp_834_Branch50ActivePower OBJECT-TYPE
		SYNTAX Integer32
		
		MAX-ACCESS read-only
		STATUS current
		DESCRIPTION
		"upsApm160snmp_834_Branch50ActivePower stored as 0.01kW."
		::= { upsApm160snmpEntry 834 }
upsApm160snmp_835_Branch50ApparentPower OBJECT-TYPE
		SYNTAX Integer32
		
		MAX-ACCESS read-only
		STATUS current
		DESCRIPTION
		"upsApm160snmp_835_Branch50ApparentPower stored as 0.01kVA."
		::= { upsApm160snmpEntry 835 }
upsApm160snmp_836_Branch50THDi OBJECT-TYPE
		SYNTAX Integer32
		
		MAX-ACCESS read-only
		STATUS current
		DESCRIPTION
		"upsApm160snmp_836_Branch50THDi stored as 0.01%."
		::= { upsApm160snmpEntry 836 }
upsApm160snmp_837_Branch50RatedCurrent OBJECT-TYPE
		SYNTAX Integer32
		
		MAX-ACCESS read-only
		STATUS current
		DESCRIPTION
		"upsApm160snmp_837_Branch50RatedCurrent stored as 0.01A."
		::= { upsApm160snmpEntry 837 }
upsApm160snmp_838_Branch50LoadRatio OBJECT-TYPE
		SYNTAX Integer32
		
		MAX-ACCESS read-only
		STATUS current
		DESCRIPTION
		"upsApm160snmp_838_Branch50LoadRatio stored as 0.01%."
		::= { upsApm160snmpEntry 838 }
upsApm160snmp_839_Branch50PowerFactor OBJECT-TYPE
		SYNTAX Integer32
		
		MAX-ACCESS read-only
		STATUS current
		DESCRIPTION
		"upsApm160snmp_839_Branch50PowerFactor stored as 0.01."
		::= { upsApm160snmpEntry 839 }
upsApm160snmp_840_Branch50Voltage OBJECT-TYPE
		SYNTAX Integer32
		
		MAX-ACCESS read-only
		STATUS current
		DESCRIPTION
		"upsApm160snmp_840_Branch50Voltage stored as 0.01V."
		::= { upsApm160snmpEntry 840 }
upsApm160snmp_841_Branch51Current OBJECT-TYPE
		SYNTAX Integer32
		
		MAX-ACCESS read-only
		STATUS current
		DESCRIPTION
		"upsApm160snmp_841_Branch51Current stored as 0.01A."
		::= { upsApm160snmpEntry 841 }
upsApm160snmp_842_Branch51Energy OBJECT-TYPE
		SYNTAX Integer32
		
		MAX-ACCESS read-only
		STATUS current
		DESCRIPTION
		"upsApm160snmp_842_Branch51Energy stored as 0.01kWh."
		::= { upsApm160snmpEntry 842 }
upsApm160snmp_843_Branch51SwitchStatus OBJECT-TYPE
		SYNTAX INTEGER {
			open(0),
			close(1) }
		MAX-ACCESS read-only
		STATUS current
		DESCRIPTION
		"upsApm160snmp_843_Branch51SwitchStatus status."
		::= { upsApm160snmpEntry 843 }
upsApm160snmp_844_Branch51ActivePower OBJECT-TYPE
		SYNTAX Integer32
		
		MAX-ACCESS read-only
		STATUS current
		DESCRIPTION
		"upsApm160snmp_844_Branch51ActivePower stored as 0.01kW."
		::= { upsApm160snmpEntry 844 }
upsApm160snmp_845_Branch51ApparentPower OBJECT-TYPE
		SYNTAX Integer32
		
		MAX-ACCESS read-only
		STATUS current
		DESCRIPTION
		"upsApm160snmp_845_Branch51ApparentPower stored as 0.01kVA."
		::= { upsApm160snmpEntry 845 }
upsApm160snmp_846_Branch51THDi OBJECT-TYPE
		SYNTAX Integer32
		
		MAX-ACCESS read-only
		STATUS current
		DESCRIPTION
		"upsApm160snmp_846_Branch51THDi stored as 0.01%."
		::= { upsApm160snmpEntry 846 }
upsApm160snmp_847_Branch51RatedCurrent OBJECT-TYPE
		SYNTAX Integer32
		
		MAX-ACCESS read-only
		STATUS current
		DESCRIPTION
		"upsApm160snmp_847_Branch51RatedCurrent stored as 0.01A."
		::= { upsApm160snmpEntry 847 }
upsApm160snmp_848_Branch51LoadRatio OBJECT-TYPE
		SYNTAX Integer32
		
		MAX-ACCESS read-only
		STATUS current
		DESCRIPTION
		"upsApm160snmp_848_Branch51LoadRatio stored as 0.01%."
		::= { upsApm160snmpEntry 848 }
upsApm160snmp_849_Branch51PowerFactor OBJECT-TYPE
		SYNTAX Integer32
		
		MAX-ACCESS read-only
		STATUS current
		DESCRIPTION
		"upsApm160snmp_849_Branch51PowerFactor stored as 0.01."
		::= { upsApm160snmpEntry 849 }
upsApm160snmp_850_Branch51Voltage OBJECT-TYPE
		SYNTAX Integer32
		
		MAX-ACCESS read-only
		STATUS current
		DESCRIPTION
		"upsApm160snmp_850_Branch51Voltage stored as 0.01V."
		::= { upsApm160snmpEntry 850 }
upsApm160snmp_851_Branch52Current OBJECT-TYPE
		SYNTAX Integer32
		
		MAX-ACCESS read-only
		STATUS current
		DESCRIPTION
		"upsApm160snmp_851_Branch52Current stored as 0.01A."
		::= { upsApm160snmpEntry 851 }
upsApm160snmp_852_Branch52Energy OBJECT-TYPE
		SYNTAX Integer32
		
		MAX-ACCESS read-only
		STATUS current
		DESCRIPTION
		"upsApm160snmp_852_Branch52Energy stored as 0.01kWh."
		::= { upsApm160snmpEntry 852 }
upsApm160snmp_853_Branch52SwitchStatus OBJECT-TYPE
		SYNTAX INTEGER {
			open(0),
			close(1) }
		MAX-ACCESS read-only
		STATUS current
		DESCRIPTION
		"upsApm160snmp_853_Branch52SwitchStatus status."
		::= { upsApm160snmpEntry 853 }
upsApm160snmp_854_Branch52ActivePower OBJECT-TYPE
		SYNTAX Integer32
		
		MAX-ACCESS read-only
		STATUS current
		DESCRIPTION
		"upsApm160snmp_854_Branch52ActivePower stored as 0.01kW."
		::= { upsApm160snmpEntry 854 }
upsApm160snmp_855_Branch52ApparentPower OBJECT-TYPE
		SYNTAX Integer32
		
		MAX-ACCESS read-only
		STATUS current
		DESCRIPTION
		"upsApm160snmp_855_Branch52ApparentPower stored as 0.01kVA."
		::= { upsApm160snmpEntry 855 }
upsApm160snmp_856_Branch52THDi OBJECT-TYPE
		SYNTAX Integer32
		
		MAX-ACCESS read-only
		STATUS current
		DESCRIPTION
		"upsApm160snmp_856_Branch52THDi stored as 0.01%."
		::= { upsApm160snmpEntry 856 }
upsApm160snmp_857_Branch52RatedCurrent OBJECT-TYPE
		SYNTAX Integer32
		
		MAX-ACCESS read-only
		STATUS current
		DESCRIPTION
		"upsApm160snmp_857_Branch52RatedCurrent stored as 0.01A."
		::= { upsApm160snmpEntry 857 }
upsApm160snmp_858_Branch52LoadRatio OBJECT-TYPE
		SYNTAX Integer32
		
		MAX-ACCESS read-only
		STATUS current
		DESCRIPTION
		"upsApm160snmp_858_Branch52LoadRatio stored as 0.01%."
		::= { upsApm160snmpEntry 858 }
upsApm160snmp_859_Branch52PowerFactor OBJECT-TYPE
		SYNTAX Integer32
		
		MAX-ACCESS read-only
		STATUS current
		DESCRIPTION
		"upsApm160snmp_859_Branch52PowerFactor stored as 0.01."
		::= { upsApm160snmpEntry 859 }
upsApm160snmp_860_Branch52Voltage OBJECT-TYPE
		SYNTAX Integer32
		
		MAX-ACCESS read-only
		STATUS current
		DESCRIPTION
		"upsApm160snmp_860_Branch52Voltage stored as 0.01V."
		::= { upsApm160snmpEntry 860 }
upsApm160snmp_861_Branch53Current OBJECT-TYPE
		SYNTAX Integer32
		
		MAX-ACCESS read-only
		STATUS current
		DESCRIPTION
		"upsApm160snmp_861_Branch53Current stored as 0.01A."
		::= { upsApm160snmpEntry 861 }
upsApm160snmp_862_Branch53Energy OBJECT-TYPE
		SYNTAX Integer32
		
		MAX-ACCESS read-only
		STATUS current
		DESCRIPTION
		"upsApm160snmp_862_Branch53Energy stored as 0.01kWh."
		::= { upsApm160snmpEntry 862 }
upsApm160snmp_863_Branch53SwitchStatus OBJECT-TYPE
		SYNTAX INTEGER {
			open(0),
			close(1) }
		MAX-ACCESS read-only
		STATUS current
		DESCRIPTION
		"upsApm160snmp_863_Branch53SwitchStatus status."
		::= { upsApm160snmpEntry 863 }
upsApm160snmp_864_Branch53ActivePower OBJECT-TYPE
		SYNTAX Integer32
		
		MAX-ACCESS read-only
		STATUS current
		DESCRIPTION
		"upsApm160snmp_864_Branch53ActivePower stored as 0.01kW."
		::= { upsApm160snmpEntry 864 }
upsApm160snmp_865_Branch53ApparentPower OBJECT-TYPE
		SYNTAX Integer32
		
		MAX-ACCESS read-only
		STATUS current
		DESCRIPTION
		"upsApm160snmp_865_Branch53ApparentPower stored as 0.01kVA."
		::= { upsApm160snmpEntry 865 }
upsApm160snmp_866_Branch53THDi OBJECT-TYPE
		SYNTAX Integer32
		
		MAX-ACCESS read-only
		STATUS current
		DESCRIPTION
		"upsApm160snmp_866_Branch53THDi stored as 0.01%."
		::= { upsApm160snmpEntry 866 }
upsApm160snmp_867_Branch53RatedCurrent OBJECT-TYPE
		SYNTAX Integer32
		
		MAX-ACCESS read-only
		STATUS current
		DESCRIPTION
		"upsApm160snmp_867_Branch53RatedCurrent stored as 0.01A."
		::= { upsApm160snmpEntry 867 }
upsApm160snmp_868_Branch53LoadRatio OBJECT-TYPE
		SYNTAX Integer32
		
		MAX-ACCESS read-only
		STATUS current
		DESCRIPTION
		"upsApm160snmp_868_Branch53LoadRatio stored as 0.01%."
		::= { upsApm160snmpEntry 868 }
upsApm160snmp_869_Branch53PowerFactor OBJECT-TYPE
		SYNTAX Integer32
		
		MAX-ACCESS read-only
		STATUS current
		DESCRIPTION
		"upsApm160snmp_869_Branch53PowerFactor stored as 0.01."
		::= { upsApm160snmpEntry 869 }
upsApm160snmp_870_Branch53Voltage OBJECT-TYPE
		SYNTAX Integer32
		
		MAX-ACCESS read-only
		STATUS current
		DESCRIPTION
		"upsApm160snmp_870_Branch53Voltage stored as 0.01V."
		::= { upsApm160snmpEntry 870 }
upsApm160snmp_871_Branch54Current OBJECT-TYPE
		SYNTAX Integer32
		
		MAX-ACCESS read-only
		STATUS current
		DESCRIPTION
		"upsApm160snmp_871_Branch54Current stored as 0.01A."
		::= { upsApm160snmpEntry 871 }
upsApm160snmp_872_Branch54Energy OBJECT-TYPE
		SYNTAX Integer32
		
		MAX-ACCESS read-only
		STATUS current
		DESCRIPTION
		"upsApm160snmp_872_Branch54Energy stored as 0.01kWh."
		::= { upsApm160snmpEntry 872 }
upsApm160snmp_873_Branch54SwitchStatus OBJECT-TYPE
		SYNTAX INTEGER {
			open(0),
			close(1) }
		MAX-ACCESS read-only
		STATUS current
		DESCRIPTION
		"upsApm160snmp_873_Branch54SwitchStatus status."
		::= { upsApm160snmpEntry 873 }
upsApm160snmp_874_Branch54ActivePower OBJECT-TYPE
		SYNTAX Integer32
		
		MAX-ACCESS read-only
		STATUS current
		DESCRIPTION
		"upsApm160snmp_874_Branch54ActivePower stored as 0.01kW."
		::= { upsApm160snmpEntry 874 }
upsApm160snmp_875_Branch54ApparentPower OBJECT-TYPE
		SYNTAX Integer32
		
		MAX-ACCESS read-only
		STATUS current
		DESCRIPTION
		"upsApm160snmp_875_Branch54ApparentPower stored as 0.01kVA."
		::= { upsApm160snmpEntry 875 }
upsApm160snmp_876_Branch54THDi OBJECT-TYPE
		SYNTAX Integer32
		
		MAX-ACCESS read-only
		STATUS current
		DESCRIPTION
		"upsApm160snmp_876_Branch54THDi stored as 0.01%."
		::= { upsApm160snmpEntry 876 }
upsApm160snmp_877_Branch54RatedCurrent OBJECT-TYPE
		SYNTAX Integer32
		
		MAX-ACCESS read-only
		STATUS current
		DESCRIPTION
		"upsApm160snmp_877_Branch54RatedCurrent stored as 0.01A."
		::= { upsApm160snmpEntry 877 }
upsApm160snmp_878_Branch54LoadRatio OBJECT-TYPE
		SYNTAX Integer32
		
		MAX-ACCESS read-only
		STATUS current
		DESCRIPTION
		"upsApm160snmp_878_Branch54LoadRatio stored as 0.01%."
		::= { upsApm160snmpEntry 878 }
upsApm160snmp_879_Branch54PowerFactor OBJECT-TYPE
		SYNTAX Integer32
		
		MAX-ACCESS read-only
		STATUS current
		DESCRIPTION
		"upsApm160snmp_879_Branch54PowerFactor stored as 0.01."
		::= { upsApm160snmpEntry 879 }
upsApm160snmp_880_Branch54Voltage OBJECT-TYPE
		SYNTAX Integer32
		
		MAX-ACCESS read-only
		STATUS current
		DESCRIPTION
		"upsApm160snmp_880_Branch54Voltage stored as 0.01V."
		::= { upsApm160snmpEntry 880 }
upsApm160snmp_881_Branch55Current OBJECT-TYPE
		SYNTAX Integer32
		
		MAX-ACCESS read-only
		STATUS current
		DESCRIPTION
		"upsApm160snmp_881_Branch55Current stored as 0.01A."
		::= { upsApm160snmpEntry 881 }
upsApm160snmp_882_Branch55Energy OBJECT-TYPE
		SYNTAX Integer32
		
		MAX-ACCESS read-only
		STATUS current
		DESCRIPTION
		"upsApm160snmp_882_Branch55Energy stored as 0.01kWh."
		::= { upsApm160snmpEntry 882 }
upsApm160snmp_883_Branch55SwitchStatus OBJECT-TYPE
		SYNTAX INTEGER {
			open(0),
			close(1) }
		MAX-ACCESS read-only
		STATUS current
		DESCRIPTION
		"upsApm160snmp_883_Branch55SwitchStatus status."
		::= { upsApm160snmpEntry 883 }
upsApm160snmp_884_Branch55ActivePower OBJECT-TYPE
		SYNTAX Integer32
		
		MAX-ACCESS read-only
		STATUS current
		DESCRIPTION
		"upsApm160snmp_884_Branch55ActivePower stored as 0.01kW."
		::= { upsApm160snmpEntry 884 }
upsApm160snmp_885_Branch55ApparentPower OBJECT-TYPE
		SYNTAX Integer32
		
		MAX-ACCESS read-only
		STATUS current
		DESCRIPTION
		"upsApm160snmp_885_Branch55ApparentPower stored as 0.01kVA."
		::= { upsApm160snmpEntry 885 }
upsApm160snmp_886_Branch55THDi OBJECT-TYPE
		SYNTAX Integer32
		
		MAX-ACCESS read-only
		STATUS current
		DESCRIPTION
		"upsApm160snmp_886_Branch55THDi stored as 0.01%."
		::= { upsApm160snmpEntry 886 }
upsApm160snmp_887_Branch55RatedCurrent OBJECT-TYPE
		SYNTAX Integer32
		
		MAX-ACCESS read-only
		STATUS current
		DESCRIPTION
		"upsApm160snmp_887_Branch55RatedCurrent stored as 0.01A."
		::= { upsApm160snmpEntry 887 }
upsApm160snmp_888_Branch55LoadRatio OBJECT-TYPE
		SYNTAX Integer32
		
		MAX-ACCESS read-only
		STATUS current
		DESCRIPTION
		"upsApm160snmp_888_Branch55LoadRatio stored as 0.01%."
		::= { upsApm160snmpEntry 888 }
upsApm160snmp_889_Branch55PowerFactor OBJECT-TYPE
		SYNTAX Integer32
		
		MAX-ACCESS read-only
		STATUS current
		DESCRIPTION
		"upsApm160snmp_889_Branch55PowerFactor stored as 0.01."
		::= { upsApm160snmpEntry 889 }
upsApm160snmp_890_Branch55Voltage OBJECT-TYPE
		SYNTAX Integer32
		
		MAX-ACCESS read-only
		STATUS current
		DESCRIPTION
		"upsApm160snmp_890_Branch55Voltage stored as 0.01V."
		::= { upsApm160snmpEntry 890 }
upsApm160snmp_891_Branch56Current OBJECT-TYPE
		SYNTAX Integer32
		
		MAX-ACCESS read-only
		STATUS current
		DESCRIPTION
		"upsApm160snmp_891_Branch56Current stored as 0.01A."
		::= { upsApm160snmpEntry 891 }
upsApm160snmp_892_Branch56Energy OBJECT-TYPE
		SYNTAX Integer32
		
		MAX-ACCESS read-only
		STATUS current
		DESCRIPTION
		"upsApm160snmp_892_Branch56Energy stored as 0.01kWh."
		::= { upsApm160snmpEntry 892 }
upsApm160snmp_893_Branch56SwitchStatus OBJECT-TYPE
		SYNTAX INTEGER {
			open(0),
			close(1) }
		MAX-ACCESS read-only
		STATUS current
		DESCRIPTION
		"upsApm160snmp_893_Branch56SwitchStatus status."
		::= { upsApm160snmpEntry 893 }
upsApm160snmp_894_Branch56ActivePower OBJECT-TYPE
		SYNTAX Integer32
		
		MAX-ACCESS read-only
		STATUS current
		DESCRIPTION
		"upsApm160snmp_894_Branch56ActivePower stored as 0.01kW."
		::= { upsApm160snmpEntry 894 }
upsApm160snmp_895_Branch56ApparentPower OBJECT-TYPE
		SYNTAX Integer32
		
		MAX-ACCESS read-only
		STATUS current
		DESCRIPTION
		"upsApm160snmp_895_Branch56ApparentPower stored as 0.01kVA."
		::= { upsApm160snmpEntry 895 }
upsApm160snmp_896_Branch56THDi OBJECT-TYPE
		SYNTAX Integer32
		
		MAX-ACCESS read-only
		STATUS current
		DESCRIPTION
		"upsApm160snmp_896_Branch56THDi stored as 0.01%."
		::= { upsApm160snmpEntry 896 }
upsApm160snmp_897_Branch56RatedCurrent OBJECT-TYPE
		SYNTAX Integer32
		
		MAX-ACCESS read-only
		STATUS current
		DESCRIPTION
		"upsApm160snmp_897_Branch56RatedCurrent stored as 0.01A."
		::= { upsApm160snmpEntry 897 }
upsApm160snmp_898_Branch56LoadRatio OBJECT-TYPE
		SYNTAX Integer32
		
		MAX-ACCESS read-only
		STATUS current
		DESCRIPTION
		"upsApm160snmp_898_Branch56LoadRatio stored as 0.01%."
		::= { upsApm160snmpEntry 898 }
upsApm160snmp_899_Branch56PowerFactor OBJECT-TYPE
		SYNTAX Integer32
		
		MAX-ACCESS read-only
		STATUS current
		DESCRIPTION
		"upsApm160snmp_899_Branch56PowerFactor stored as 0.01."
		::= { upsApm160snmpEntry 899 }
upsApm160snmp_900_Branch56Voltage OBJECT-TYPE
		SYNTAX Integer32
		
		MAX-ACCESS read-only
		STATUS current
		DESCRIPTION
		"upsApm160snmp_900_Branch56Voltage stored as 0.01V."
		::= { upsApm160snmpEntry 900 }
upsApm160snmp_901_Branch57Current OBJECT-TYPE
		SYNTAX Integer32
		
		MAX-ACCESS read-only
		STATUS current
		DESCRIPTION
		"upsApm160snmp_901_Branch57Current stored as 0.01A."
		::= { upsApm160snmpEntry 901 }
upsApm160snmp_902_Branch57Energy OBJECT-TYPE
		SYNTAX Integer32
		
		MAX-ACCESS read-only
		STATUS current
		DESCRIPTION
		"upsApm160snmp_902_Branch57Energy stored as 0.01kWh."
		::= { upsApm160snmpEntry 902 }
upsApm160snmp_903_Branch57SwitchStatus OBJECT-TYPE
		SYNTAX INTEGER {
			open(0),
			close(1) }
		MAX-ACCESS read-only
		STATUS current
		DESCRIPTION
		"upsApm160snmp_903_Branch57SwitchStatus status."
		::= { upsApm160snmpEntry 903 }
upsApm160snmp_904_Branch57ActivePower OBJECT-TYPE
		SYNTAX Integer32
		
		MAX-ACCESS read-only
		STATUS current
		DESCRIPTION
		"upsApm160snmp_904_Branch57ActivePower stored as 0.01kW."
		::= { upsApm160snmpEntry 904 }
upsApm160snmp_905_Branch57ApparentPower OBJECT-TYPE
		SYNTAX Integer32
		
		MAX-ACCESS read-only
		STATUS current
		DESCRIPTION
		"upsApm160snmp_905_Branch57ApparentPower stored as 0.01kVA."
		::= { upsApm160snmpEntry 905 }
upsApm160snmp_906_Branch57THDi OBJECT-TYPE
		SYNTAX Integer32
		
		MAX-ACCESS read-only
		STATUS current
		DESCRIPTION
		"upsApm160snmp_906_Branch57THDi stored as 0.01%."
		::= { upsApm160snmpEntry 906 }
upsApm160snmp_907_Branch57RatedCurrent OBJECT-TYPE
		SYNTAX Integer32
		
		MAX-ACCESS read-only
		STATUS current
		DESCRIPTION
		"upsApm160snmp_907_Branch57RatedCurrent stored as 0.01A."
		::= { upsApm160snmpEntry 907 }
upsApm160snmp_908_Branch57LoadRatio OBJECT-TYPE
		SYNTAX Integer32
		
		MAX-ACCESS read-only
		STATUS current
		DESCRIPTION
		"upsApm160snmp_908_Branch57LoadRatio stored as 0.01%."
		::= { upsApm160snmpEntry 908 }
upsApm160snmp_909_Branch57PowerFactor OBJECT-TYPE
		SYNTAX Integer32
		
		MAX-ACCESS read-only
		STATUS current
		DESCRIPTION
		"upsApm160snmp_909_Branch57PowerFactor stored as 0.01."
		::= { upsApm160snmpEntry 909 }
upsApm160snmp_910_Branch57Voltage OBJECT-TYPE
		SYNTAX Integer32
		
		MAX-ACCESS read-only
		STATUS current
		DESCRIPTION
		"upsApm160snmp_910_Branch57Voltage stored as 0.01V."
		::= { upsApm160snmpEntry 910 }
upsApm160snmp_911_Branch58Current OBJECT-TYPE
		SYNTAX Integer32
		
		MAX-ACCESS read-only
		STATUS current
		DESCRIPTION
		"upsApm160snmp_911_Branch58Current stored as 0.01A."
		::= { upsApm160snmpEntry 911 }
upsApm160snmp_912_Branch58Energy OBJECT-TYPE
		SYNTAX Integer32
		
		MAX-ACCESS read-only
		STATUS current
		DESCRIPTION
		"upsApm160snmp_912_Branch58Energy stored as 0.01kWh."
		::= { upsApm160snmpEntry 912 }
upsApm160snmp_913_Branch58SwitchStatus OBJECT-TYPE
		SYNTAX INTEGER {
			open(0),
			close(1) }
		MAX-ACCESS read-only
		STATUS current
		DESCRIPTION
		"upsApm160snmp_913_Branch58SwitchStatus status."
		::= { upsApm160snmpEntry 913 }
upsApm160snmp_914_Branch58ActivePower OBJECT-TYPE
		SYNTAX Integer32
		
		MAX-ACCESS read-only
		STATUS current
		DESCRIPTION
		"upsApm160snmp_914_Branch58ActivePower stored as 0.01kW."
		::= { upsApm160snmpEntry 914 }
upsApm160snmp_915_Branch58ApparentPower OBJECT-TYPE
		SYNTAX Integer32
		
		MAX-ACCESS read-only
		STATUS current
		DESCRIPTION
		"upsApm160snmp_915_Branch58ApparentPower stored as 0.01kVA."
		::= { upsApm160snmpEntry 915 }
upsApm160snmp_916_Branch58THDi OBJECT-TYPE
		SYNTAX Integer32
		
		MAX-ACCESS read-only
		STATUS current
		DESCRIPTION
		"upsApm160snmp_916_Branch58THDi stored as 0.01%."
		::= { upsApm160snmpEntry 916 }
upsApm160snmp_917_Branch58RatedCurrent OBJECT-TYPE
		SYNTAX Integer32
		
		MAX-ACCESS read-only
		STATUS current
		DESCRIPTION
		"upsApm160snmp_917_Branch58RatedCurrent stored as 0.01A."
		::= { upsApm160snmpEntry 917 }
upsApm160snmp_918_Branch58LoadRatio OBJECT-TYPE
		SYNTAX Integer32
		
		MAX-ACCESS read-only
		STATUS current
		DESCRIPTION
		"upsApm160snmp_918_Branch58LoadRatio stored as 0.01%."
		::= { upsApm160snmpEntry 918 }
upsApm160snmp_919_Branch58PowerFactor OBJECT-TYPE
		SYNTAX Integer32
		
		MAX-ACCESS read-only
		STATUS current
		DESCRIPTION
		"upsApm160snmp_919_Branch58PowerFactor stored as 0.01."
		::= { upsApm160snmpEntry 919 }
upsApm160snmp_920_Branch58Voltage OBJECT-TYPE
		SYNTAX Integer32
		
		MAX-ACCESS read-only
		STATUS current
		DESCRIPTION
		"upsApm160snmp_920_Branch58Voltage stored as 0.01V."
		::= { upsApm160snmpEntry 920 }
upsApm160snmp_921_Branch59Current OBJECT-TYPE
		SYNTAX Integer32
		
		MAX-ACCESS read-only
		STATUS current
		DESCRIPTION
		"upsApm160snmp_921_Branch59Current stored as 0.01A."
		::= { upsApm160snmpEntry 921 }
upsApm160snmp_922_Branch59Energy OBJECT-TYPE
		SYNTAX Integer32
		
		MAX-ACCESS read-only
		STATUS current
		DESCRIPTION
		"upsApm160snmp_922_Branch59Energy stored as 0.01kWh."
		::= { upsApm160snmpEntry 922 }
upsApm160snmp_923_Branch59SwitchStatus OBJECT-TYPE
		SYNTAX INTEGER {
			open(0),
			close(1) }
		MAX-ACCESS read-only
		STATUS current
		DESCRIPTION
		"upsApm160snmp_923_Branch59SwitchStatus status."
		::= { upsApm160snmpEntry 923 }
upsApm160snmp_924_Branch59ActivePower OBJECT-TYPE
		SYNTAX Integer32
		
		MAX-ACCESS read-only
		STATUS current
		DESCRIPTION
		"upsApm160snmp_924_Branch59ActivePower stored as 0.01kW."
		::= { upsApm160snmpEntry 924 }
upsApm160snmp_925_Branch59ApparentPower OBJECT-TYPE
		SYNTAX Integer32
		
		MAX-ACCESS read-only
		STATUS current
		DESCRIPTION
		"upsApm160snmp_925_Branch59ApparentPower stored as 0.01kVA."
		::= { upsApm160snmpEntry 925 }
upsApm160snmp_926_Branch59THDi OBJECT-TYPE
		SYNTAX Integer32
		
		MAX-ACCESS read-only
		STATUS current
		DESCRIPTION
		"upsApm160snmp_926_Branch59THDi stored as 0.01%."
		::= { upsApm160snmpEntry 926 }
upsApm160snmp_927_Branch59RatedCurrent OBJECT-TYPE
		SYNTAX Integer32
		
		MAX-ACCESS read-only
		STATUS current
		DESCRIPTION
		"upsApm160snmp_927_Branch59RatedCurrent stored as 0.01A."
		::= { upsApm160snmpEntry 927 }
upsApm160snmp_928_Branch59LoadRatio OBJECT-TYPE
		SYNTAX Integer32
		
		MAX-ACCESS read-only
		STATUS current
		DESCRIPTION
		"upsApm160snmp_928_Branch59LoadRatio stored as 0.01%."
		::= { upsApm160snmpEntry 928 }
upsApm160snmp_929_Branch59PowerFactor OBJECT-TYPE
		SYNTAX Integer32
		
		MAX-ACCESS read-only
		STATUS current
		DESCRIPTION
		"upsApm160snmp_929_Branch59PowerFactor stored as 0.01."
		::= { upsApm160snmpEntry 929 }
upsApm160snmp_930_Branch59Voltage OBJECT-TYPE
		SYNTAX Integer32
		
		MAX-ACCESS read-only
		STATUS current
		DESCRIPTION
		"upsApm160snmp_930_Branch59Voltage stored as 0.01V."
		::= { upsApm160snmpEntry 930 }
upsApm160snmp_931_Branch60Current OBJECT-TYPE
		SYNTAX Integer32
		
		MAX-ACCESS read-only
		STATUS current
		DESCRIPTION
		"upsApm160snmp_931_Branch60Current stored as 0.01A."
		::= { upsApm160snmpEntry 931 }
upsApm160snmp_932_Branch60Energy OBJECT-TYPE
		SYNTAX Integer32
		
		MAX-ACCESS read-only
		STATUS current
		DESCRIPTION
		"upsApm160snmp_932_Branch60Energy stored as 0.01kWh."
		::= { upsApm160snmpEntry 932 }
upsApm160snmp_933_Branch60SwitchStatus OBJECT-TYPE
		SYNTAX INTEGER {
			open(0),
			close(1) }
		MAX-ACCESS read-only
		STATUS current
		DESCRIPTION
		"upsApm160snmp_933_Branch60SwitchStatus status."
		::= { upsApm160snmpEntry 933 }
upsApm160snmp_934_Branch60ActivePower OBJECT-TYPE
		SYNTAX Integer32
		
		MAX-ACCESS read-only
		STATUS current
		DESCRIPTION
		"upsApm160snmp_934_Branch60ActivePower stored as 0.01kW."
		::= { upsApm160snmpEntry 934 }
upsApm160snmp_935_Branch60ApparentPower OBJECT-TYPE
		SYNTAX Integer32
		
		MAX-ACCESS read-only
		STATUS current
		DESCRIPTION
		"upsApm160snmp_935_Branch60ApparentPower stored as 0.01kVA."
		::= { upsApm160snmpEntry 935 }
upsApm160snmp_936_Branch60THDi OBJECT-TYPE
		SYNTAX Integer32
		
		MAX-ACCESS read-only
		STATUS current
		DESCRIPTION
		"upsApm160snmp_936_Branch60THDi stored as 0.01%."
		::= { upsApm160snmpEntry 936 }
upsApm160snmp_937_Branch60RatedCurrent OBJECT-TYPE
		SYNTAX Integer32
		
		MAX-ACCESS read-only
		STATUS current
		DESCRIPTION
		"upsApm160snmp_937_Branch60RatedCurrent stored as 0.01A."
		::= { upsApm160snmpEntry 937 }
upsApm160snmp_938_Branch60LoadRatio OBJECT-TYPE
		SYNTAX Integer32
		
		MAX-ACCESS read-only
		STATUS current
		DESCRIPTION
		"upsApm160snmp_938_Branch60LoadRatio stored as 0.01%."
		::= { upsApm160snmpEntry 938 }
upsApm160snmp_939_Branch60PowerFactor OBJECT-TYPE
		SYNTAX Integer32
		
		MAX-ACCESS read-only
		STATUS current
		DESCRIPTION
		"upsApm160snmp_939_Branch60PowerFactor stored as 0.01."
		::= { upsApm160snmpEntry 939 }
upsApm160snmp_940_Branch60Voltage OBJECT-TYPE
		SYNTAX Integer32
		
		MAX-ACCESS read-only
		STATUS current
		DESCRIPTION
		"upsApm160snmp_940_Branch60Voltage stored as 0.01V."
		::= { upsApm160snmpEntry 940 }
upsApm160snmp_941_Branch61Current OBJECT-TYPE
		SYNTAX Integer32
		
		MAX-ACCESS read-only
		STATUS current
		DESCRIPTION
		"upsApm160snmp_941_Branch61Current stored as 0.01A."
		::= { upsApm160snmpEntry 941 }
upsApm160snmp_942_Branch61Energy OBJECT-TYPE
		SYNTAX Integer32
		
		MAX-ACCESS read-only
		STATUS current
		DESCRIPTION
		"upsApm160snmp_942_Branch61Energy stored as 0.01kWh."
		::= { upsApm160snmpEntry 942 }
upsApm160snmp_943_Branch61SwitchStatus OBJECT-TYPE
		SYNTAX INTEGER {
			open(0),
			close(1) }
		MAX-ACCESS read-only
		STATUS current
		DESCRIPTION
		"upsApm160snmp_943_Branch61SwitchStatus status."
		::= { upsApm160snmpEntry 943 }
upsApm160snmp_944_Branch61ActivePower OBJECT-TYPE
		SYNTAX Integer32
		
		MAX-ACCESS read-only
		STATUS current
		DESCRIPTION
		"upsApm160snmp_944_Branch61ActivePower stored as 0.01kW."
		::= { upsApm160snmpEntry 944 }
upsApm160snmp_945_Branch61ApparentPower OBJECT-TYPE
		SYNTAX Integer32
		
		MAX-ACCESS read-only
		STATUS current
		DESCRIPTION
		"upsApm160snmp_945_Branch61ApparentPower stored as 0.01kVA."
		::= { upsApm160snmpEntry 945 }
upsApm160snmp_946_Branch61THDi OBJECT-TYPE
		SYNTAX Integer32
		
		MAX-ACCESS read-only
		STATUS current
		DESCRIPTION
		"upsApm160snmp_946_Branch61THDi stored as 0.01%."
		::= { upsApm160snmpEntry 946 }
upsApm160snmp_947_Branch61RatedCurrent OBJECT-TYPE
		SYNTAX Integer32
		
		MAX-ACCESS read-only
		STATUS current
		DESCRIPTION
		"upsApm160snmp_947_Branch61RatedCurrent stored as 0.01A."
		::= { upsApm160snmpEntry 947 }
upsApm160snmp_948_Branch61LoadRatio OBJECT-TYPE
		SYNTAX Integer32
		
		MAX-ACCESS read-only
		STATUS current
		DESCRIPTION
		"upsApm160snmp_948_Branch61LoadRatio stored as 0.01%."
		::= { upsApm160snmpEntry 948 }
upsApm160snmp_949_Branch61PowerFactor OBJECT-TYPE
		SYNTAX Integer32
		
		MAX-ACCESS read-only
		STATUS current
		DESCRIPTION
		"upsApm160snmp_949_Branch61PowerFactor stored as 0.01."
		::= { upsApm160snmpEntry 949 }
upsApm160snmp_950_Branch61Voltage OBJECT-TYPE
		SYNTAX Integer32
		
		MAX-ACCESS read-only
		STATUS current
		DESCRIPTION
		"upsApm160snmp_950_Branch61Voltage stored as 0.01V."
		::= { upsApm160snmpEntry 950 }
upsApm160snmp_951_Branch62Current OBJECT-TYPE
		SYNTAX Integer32
		
		MAX-ACCESS read-only
		STATUS current
		DESCRIPTION
		"upsApm160snmp_951_Branch62Current stored as 0.01A."
		::= { upsApm160snmpEntry 951 }
upsApm160snmp_952_Branch62Energy OBJECT-TYPE
		SYNTAX Integer32
		
		MAX-ACCESS read-only
		STATUS current
		DESCRIPTION
		"upsApm160snmp_952_Branch62Energy stored as 0.01kWh."
		::= { upsApm160snmpEntry 952 }
upsApm160snmp_953_Branch62SwitchStatus OBJECT-TYPE
		SYNTAX INTEGER {
			open(0),
			close(1) }
		MAX-ACCESS read-only
		STATUS current
		DESCRIPTION
		"upsApm160snmp_953_Branch62SwitchStatus status."
		::= { upsApm160snmpEntry 953 }
upsApm160snmp_954_Branch62ActivePower OBJECT-TYPE
		SYNTAX Integer32
		
		MAX-ACCESS read-only
		STATUS current
		DESCRIPTION
		"upsApm160snmp_954_Branch62ActivePower stored as 0.01kW."
		::= { upsApm160snmpEntry 954 }
upsApm160snmp_955_Branch62ApparentPower OBJECT-TYPE
		SYNTAX Integer32
		
		MAX-ACCESS read-only
		STATUS current
		DESCRIPTION
		"upsApm160snmp_955_Branch62ApparentPower stored as 0.01kVA."
		::= { upsApm160snmpEntry 955 }
upsApm160snmp_956_Branch62THDi OBJECT-TYPE
		SYNTAX Integer32
		
		MAX-ACCESS read-only
		STATUS current
		DESCRIPTION
		"upsApm160snmp_956_Branch62THDi stored as 0.01%."
		::= { upsApm160snmpEntry 956 }
upsApm160snmp_957_Branch62RatedCurrent OBJECT-TYPE
		SYNTAX Integer32
		
		MAX-ACCESS read-only
		STATUS current
		DESCRIPTION
		"upsApm160snmp_957_Branch62RatedCurrent stored as 0.01A."
		::= { upsApm160snmpEntry 957 }
upsApm160snmp_958_Branch62LoadRatio OBJECT-TYPE
		SYNTAX Integer32
		
		MAX-ACCESS read-only
		STATUS current
		DESCRIPTION
		"upsApm160snmp_958_Branch62LoadRatio stored as 0.01%."
		::= { upsApm160snmpEntry 958 }
upsApm160snmp_959_Branch62PowerFactor OBJECT-TYPE
		SYNTAX Integer32
		
		MAX-ACCESS read-only
		STATUS current
		DESCRIPTION
		"upsApm160snmp_959_Branch62PowerFactor stored as 0.01."
		::= { upsApm160snmpEntry 959 }
upsApm160snmp_960_Branch62Voltage OBJECT-TYPE
		SYNTAX Integer32
		
		MAX-ACCESS read-only
		STATUS current
		DESCRIPTION
		"upsApm160snmp_960_Branch62Voltage stored as 0.01V."
		::= { upsApm160snmpEntry 960 }
upsApm160snmp_961_Branch63Current OBJECT-TYPE
		SYNTAX Integer32
		
		MAX-ACCESS read-only
		STATUS current
		DESCRIPTION
		"upsApm160snmp_961_Branch63Current stored as 0.01A."
		::= { upsApm160snmpEntry 961 }
upsApm160snmp_962_Branch63Energy OBJECT-TYPE
		SYNTAX Integer32
		
		MAX-ACCESS read-only
		STATUS current
		DESCRIPTION
		"upsApm160snmp_962_Branch63Energy stored as 0.01kWh."
		::= { upsApm160snmpEntry 962 }
upsApm160snmp_963_Branch63SwitchStatus OBJECT-TYPE
		SYNTAX INTEGER {
			open(0),
			close(1) }
		MAX-ACCESS read-only
		STATUS current
		DESCRIPTION
		"upsApm160snmp_963_Branch63SwitchStatus status."
		::= { upsApm160snmpEntry 963 }
upsApm160snmp_964_Branch63ActivePower OBJECT-TYPE
		SYNTAX Integer32
		
		MAX-ACCESS read-only
		STATUS current
		DESCRIPTION
		"upsApm160snmp_964_Branch63ActivePower stored as 0.01kW."
		::= { upsApm160snmpEntry 964 }
upsApm160snmp_965_Branch63ApparentPower OBJECT-TYPE
		SYNTAX Integer32
		
		MAX-ACCESS read-only
		STATUS current
		DESCRIPTION
		"upsApm160snmp_965_Branch63ApparentPower stored as 0.01kVA."
		::= { upsApm160snmpEntry 965 }
upsApm160snmp_966_Branch63THDi OBJECT-TYPE
		SYNTAX Integer32
		
		MAX-ACCESS read-only
		STATUS current
		DESCRIPTION
		"upsApm160snmp_966_Branch63THDi stored as 0.01%."
		::= { upsApm160snmpEntry 966 }
upsApm160snmp_967_Branch63RatedCurrent OBJECT-TYPE
		SYNTAX Integer32
		
		MAX-ACCESS read-only
		STATUS current
		DESCRIPTION
		"upsApm160snmp_967_Branch63RatedCurrent stored as 0.01A."
		::= { upsApm160snmpEntry 967 }
upsApm160snmp_968_Branch63LoadRatio OBJECT-TYPE
		SYNTAX Integer32
		
		MAX-ACCESS read-only
		STATUS current
		DESCRIPTION
		"upsApm160snmp_968_Branch63LoadRatio stored as 0.01%."
		::= { upsApm160snmpEntry 968 }
upsApm160snmp_969_Branch63PowerFactor OBJECT-TYPE
		SYNTAX Integer32
		
		MAX-ACCESS read-only
		STATUS current
		DESCRIPTION
		"upsApm160snmp_969_Branch63PowerFactor stored as 0.01."
		::= { upsApm160snmpEntry 969 }
upsApm160snmp_970_Branch63Voltage OBJECT-TYPE
		SYNTAX Integer32
		
		MAX-ACCESS read-only
		STATUS current
		DESCRIPTION
		"upsApm160snmp_970_Branch63Voltage stored as 0.01V."
		::= { upsApm160snmpEntry 970 }
upsApm160snmp_971_Branch64Current OBJECT-TYPE
		SYNTAX Integer32
		
		MAX-ACCESS read-only
		STATUS current
		DESCRIPTION
		"upsApm160snmp_971_Branch64Current stored as 0.01A."
		::= { upsApm160snmpEntry 971 }
upsApm160snmp_972_Branch64Energy OBJECT-TYPE
		SYNTAX Integer32
		
		MAX-ACCESS read-only
		STATUS current
		DESCRIPTION
		"upsApm160snmp_972_Branch64Energy stored as 0.01kWh."
		::= { upsApm160snmpEntry 972 }
upsApm160snmp_973_Branch64SwitchStatus OBJECT-TYPE
		SYNTAX INTEGER {
			open(0),
			close(1) }
		MAX-ACCESS read-only
		STATUS current
		DESCRIPTION
		"upsApm160snmp_973_Branch64SwitchStatus status."
		::= { upsApm160snmpEntry 973 }
upsApm160snmp_974_Branch64ActivePower OBJECT-TYPE
		SYNTAX Integer32
		
		MAX-ACCESS read-only
		STATUS current
		DESCRIPTION
		"upsApm160snmp_974_Branch64ActivePower stored as 0.01kW."
		::= { upsApm160snmpEntry 974 }
upsApm160snmp_975_Branch64ApparentPower OBJECT-TYPE
		SYNTAX Integer32
		
		MAX-ACCESS read-only
		STATUS current
		DESCRIPTION
		"upsApm160snmp_975_Branch64ApparentPower stored as 0.01kVA."
		::= { upsApm160snmpEntry 975 }
upsApm160snmp_976_Branch64THDi OBJECT-TYPE
		SYNTAX Integer32
		
		MAX-ACCESS read-only
		STATUS current
		DESCRIPTION
		"upsApm160snmp_976_Branch64THDi stored as 0.01%."
		::= { upsApm160snmpEntry 976 }
upsApm160snmp_977_Branch64RatedCurrent OBJECT-TYPE
		SYNTAX Integer32
		
		MAX-ACCESS read-only
		STATUS current
		DESCRIPTION
		"upsApm160snmp_977_Branch64RatedCurrent stored as 0.01A."
		::= { upsApm160snmpEntry 977 }
upsApm160snmp_978_Branch64LoadRatio OBJECT-TYPE
		SYNTAX Integer32
		
		MAX-ACCESS read-only
		STATUS current
		DESCRIPTION
		"upsApm160snmp_978_Branch64LoadRatio stored as 0.01%."
		::= { upsApm160snmpEntry 978 }
upsApm160snmp_979_Branch64PowerFactor OBJECT-TYPE
		SYNTAX Integer32
		
		MAX-ACCESS read-only
		STATUS current
		DESCRIPTION
		"upsApm160snmp_979_Branch64PowerFactor stored as 0.01."
		::= { upsApm160snmpEntry 979 }
upsApm160snmp_980_Branch64Voltage OBJECT-TYPE
		SYNTAX Integer32
		
		MAX-ACCESS read-only
		STATUS current
		DESCRIPTION
		"upsApm160snmp_980_Branch64Voltage stored as 0.01V."
		::= { upsApm160snmpEntry 980 }
upsApm160snmp_981_Branch65Current OBJECT-TYPE
		SYNTAX Integer32
		
		MAX-ACCESS read-only
		STATUS current
		DESCRIPTION
		"upsApm160snmp_981_Branch65Current stored as 0.01A."
		::= { upsApm160snmpEntry 981 }
upsApm160snmp_982_Branch65Energy OBJECT-TYPE
		SYNTAX Integer32
		
		MAX-ACCESS read-only
		STATUS current
		DESCRIPTION
		"upsApm160snmp_982_Branch65Energy stored as 0.01kWh."
		::= { upsApm160snmpEntry 982 }
upsApm160snmp_983_Branch65SwitchStatus OBJECT-TYPE
		SYNTAX INTEGER {
			open(0),
			close(1) }
		MAX-ACCESS read-only
		STATUS current
		DESCRIPTION
		"upsApm160snmp_983_Branch65SwitchStatus status."
		::= { upsApm160snmpEntry 983 }
upsApm160snmp_984_Branch65ActivePower OBJECT-TYPE
		SYNTAX Integer32
		
		MAX-ACCESS read-only
		STATUS current
		DESCRIPTION
		"upsApm160snmp_984_Branch65ActivePower stored as 0.01kW."
		::= { upsApm160snmpEntry 984 }
upsApm160snmp_985_Branch65ApparentPower OBJECT-TYPE
		SYNTAX Integer32
		
		MAX-ACCESS read-only
		STATUS current
		DESCRIPTION
		"upsApm160snmp_985_Branch65ApparentPower stored as 0.01kVA."
		::= { upsApm160snmpEntry 985 }
upsApm160snmp_986_Branch65THDi OBJECT-TYPE
		SYNTAX Integer32
		
		MAX-ACCESS read-only
		STATUS current
		DESCRIPTION
		"upsApm160snmp_986_Branch65THDi stored as 0.01%."
		::= { upsApm160snmpEntry 986 }
upsApm160snmp_987_Branch65RatedCurrent OBJECT-TYPE
		SYNTAX Integer32
		
		MAX-ACCESS read-only
		STATUS current
		DESCRIPTION
		"upsApm160snmp_987_Branch65RatedCurrent stored as 0.01A."
		::= { upsApm160snmpEntry 987 }
upsApm160snmp_988_Branch65LoadRatio OBJECT-TYPE
		SYNTAX Integer32
		
		MAX-ACCESS read-only
		STATUS current
		DESCRIPTION
		"upsApm160snmp_988_Branch65LoadRatio stored as 0.01%."
		::= { upsApm160snmpEntry 988 }
upsApm160snmp_989_Branch65PowerFactor OBJECT-TYPE
		SYNTAX Integer32
		
		MAX-ACCESS read-only
		STATUS current
		DESCRIPTION
		"upsApm160snmp_989_Branch65PowerFactor stored as 0.01."
		::= { upsApm160snmpEntry 989 }
upsApm160snmp_990_Branch65Voltage OBJECT-TYPE
		SYNTAX Integer32
		
		MAX-ACCESS read-only
		STATUS current
		DESCRIPTION
		"upsApm160snmp_990_Branch65Voltage stored as 0.01V."
		::= { upsApm160snmpEntry 990 }
upsApm160snmp_991_Branch66Current OBJECT-TYPE
		SYNTAX Integer32
		
		MAX-ACCESS read-only
		STATUS current
		DESCRIPTION
		"upsApm160snmp_991_Branch66Current stored as 0.01A."
		::= { upsApm160snmpEntry 991 }
upsApm160snmp_992_Branch66Energy OBJECT-TYPE
		SYNTAX Integer32
		
		MAX-ACCESS read-only
		STATUS current
		DESCRIPTION
		"upsApm160snmp_992_Branch66Energy stored as 0.01kWh."
		::= { upsApm160snmpEntry 992 }
upsApm160snmp_993_Branch66SwitchStatus OBJECT-TYPE
		SYNTAX INTEGER {
			open(0),
			close(1) }
		MAX-ACCESS read-only
		STATUS current
		DESCRIPTION
		"upsApm160snmp_993_Branch66SwitchStatus status."
		::= { upsApm160snmpEntry 993 }
upsApm160snmp_994_Branch66ActivePower OBJECT-TYPE
		SYNTAX Integer32
		
		MAX-ACCESS read-only
		STATUS current
		DESCRIPTION
		"upsApm160snmp_994_Branch66ActivePower stored as 0.01kW."
		::= { upsApm160snmpEntry 994 }
upsApm160snmp_995_Branch66ApparentPower OBJECT-TYPE
		SYNTAX Integer32
		
		MAX-ACCESS read-only
		STATUS current
		DESCRIPTION
		"upsApm160snmp_995_Branch66ApparentPower stored as 0.01kVA."
		::= { upsApm160snmpEntry 995 }
upsApm160snmp_996_Branch66THDi OBJECT-TYPE
		SYNTAX Integer32
		
		MAX-ACCESS read-only
		STATUS current
		DESCRIPTION
		"upsApm160snmp_996_Branch66THDi stored as 0.01%."
		::= { upsApm160snmpEntry 996 }
upsApm160snmp_997_Branch66RatedCurrent OBJECT-TYPE
		SYNTAX Integer32
		
		MAX-ACCESS read-only
		STATUS current
		DESCRIPTION
		"upsApm160snmp_997_Branch66RatedCurrent stored as 0.01A."
		::= { upsApm160snmpEntry 997 }
upsApm160snmp_998_Branch66LoadRatio OBJECT-TYPE
		SYNTAX Integer32
		
		MAX-ACCESS read-only
		STATUS current
		DESCRIPTION
		"upsApm160snmp_998_Branch66LoadRatio stored as 0.01%."
		::= { upsApm160snmpEntry 998 }
upsApm160snmp_999_Branch66PowerFactor OBJECT-TYPE
		SYNTAX Integer32
		
		MAX-ACCESS read-only
		STATUS current
		DESCRIPTION
		"upsApm160snmp_999_Branch66PowerFactor stored as 0.01."
		::= { upsApm160snmpEntry 999 }
upsApm160snmp_1000_Branch66Voltage OBJECT-TYPE
		SYNTAX Integer32
		
		MAX-ACCESS read-only
		STATUS current
		DESCRIPTION
		"upsApm160snmp_1000_Branch66Voltage stored as 0.01V."
		::= { upsApm160snmpEntry 1000 }
upsApm160snmp_1001_Branch67Current OBJECT-TYPE
		SYNTAX Integer32
		
		MAX-ACCESS read-only
		STATUS current
		DESCRIPTION
		"upsApm160snmp_1001_Branch67Current stored as 0.01A."
		::= { upsApm160snmpEntry 1001 }
upsApm160snmp_1002_Branch67Energy OBJECT-TYPE
		SYNTAX Integer32
		
		MAX-ACCESS read-only
		STATUS current
		DESCRIPTION
		"upsApm160snmp_1002_Branch67Energy stored as 0.01kWh."
		::= { upsApm160snmpEntry 1002 }
upsApm160snmp_1003_Branch67SwitchStatus OBJECT-TYPE
		SYNTAX INTEGER {
			open(0),
			close(1) }
		MAX-ACCESS read-only
		STATUS current
		DESCRIPTION
		"upsApm160snmp_1003_Branch67SwitchStatus status."
		::= { upsApm160snmpEntry 1003 }
upsApm160snmp_1004_Branch67ActivePower OBJECT-TYPE
		SYNTAX Integer32
		
		MAX-ACCESS read-only
		STATUS current
		DESCRIPTION
		"upsApm160snmp_1004_Branch67ActivePower stored as 0.01kW."
		::= { upsApm160snmpEntry 1004 }
upsApm160snmp_1005_Branch67ApparentPower OBJECT-TYPE
		SYNTAX Integer32
		
		MAX-ACCESS read-only
		STATUS current
		DESCRIPTION
		"upsApm160snmp_1005_Branch67ApparentPower stored as 0.01kVA."
		::= { upsApm160snmpEntry 1005 }
upsApm160snmp_1006_Branch67THDi OBJECT-TYPE
		SYNTAX Integer32
		
		MAX-ACCESS read-only
		STATUS current
		DESCRIPTION
		"upsApm160snmp_1006_Branch67THDi stored as 0.01%."
		::= { upsApm160snmpEntry 1006 }
upsApm160snmp_1007_Branch67RatedCurrent OBJECT-TYPE
		SYNTAX Integer32
		
		MAX-ACCESS read-only
		STATUS current
		DESCRIPTION
		"upsApm160snmp_1007_Branch67RatedCurrent stored as 0.01A."
		::= { upsApm160snmpEntry 1007 }
upsApm160snmp_1008_Branch67LoadRatio OBJECT-TYPE
		SYNTAX Integer32
		
		MAX-ACCESS read-only
		STATUS current
		DESCRIPTION
		"upsApm160snmp_1008_Branch67LoadRatio stored as 0.01%."
		::= { upsApm160snmpEntry 1008 }
upsApm160snmp_1009_Branch67PowerFactor OBJECT-TYPE
		SYNTAX Integer32
		
		MAX-ACCESS read-only
		STATUS current
		DESCRIPTION
		"upsApm160snmp_1009_Branch67PowerFactor stored as 0.01."
		::= { upsApm160snmpEntry 1009 }
upsApm160snmp_1010_Branch67Voltage OBJECT-TYPE
		SYNTAX Integer32
		
		MAX-ACCESS read-only
		STATUS current
		DESCRIPTION
		"upsApm160snmp_1010_Branch67Voltage stored as 0.01V."
		::= { upsApm160snmpEntry 1010 }
upsApm160snmp_1011_Branch68Current OBJECT-TYPE
		SYNTAX Integer32
		
		MAX-ACCESS read-only
		STATUS current
		DESCRIPTION
		"upsApm160snmp_1011_Branch68Current stored as 0.01A."
		::= { upsApm160snmpEntry 1011 }
upsApm160snmp_1012_Branch68Energy OBJECT-TYPE
		SYNTAX Integer32
		
		MAX-ACCESS read-only
		STATUS current
		DESCRIPTION
		"upsApm160snmp_1012_Branch68Energy stored as 0.01kWh."
		::= { upsApm160snmpEntry 1012 }
upsApm160snmp_1013_Branch68SwitchStatus OBJECT-TYPE
		SYNTAX INTEGER {
			open(0),
			close(1) }
		MAX-ACCESS read-only
		STATUS current
		DESCRIPTION
		"upsApm160snmp_1013_Branch68SwitchStatus status."
		::= { upsApm160snmpEntry 1013 }
upsApm160snmp_1014_Branch68ActivePower OBJECT-TYPE
		SYNTAX Integer32
		
		MAX-ACCESS read-only
		STATUS current
		DESCRIPTION
		"upsApm160snmp_1014_Branch68ActivePower stored as 0.01kW."
		::= { upsApm160snmpEntry 1014 }
upsApm160snmp_1015_Branch68ApparentPower OBJECT-TYPE
		SYNTAX Integer32
		
		MAX-ACCESS read-only
		STATUS current
		DESCRIPTION
		"upsApm160snmp_1015_Branch68ApparentPower stored as 0.01kVA."
		::= { upsApm160snmpEntry 1015 }
upsApm160snmp_1016_Branch68THDi OBJECT-TYPE
		SYNTAX Integer32
		
		MAX-ACCESS read-only
		STATUS current
		DESCRIPTION
		"upsApm160snmp_1016_Branch68THDi stored as 0.01%."
		::= { upsApm160snmpEntry 1016 }
upsApm160snmp_1017_Branch68RatedCurrent OBJECT-TYPE
		SYNTAX Integer32
		
		MAX-ACCESS read-only
		STATUS current
		DESCRIPTION
		"upsApm160snmp_1017_Branch68RatedCurrent stored as 0.01A."
		::= { upsApm160snmpEntry 1017 }
upsApm160snmp_1018_Branch68LoadRatio OBJECT-TYPE
		SYNTAX Integer32
		
		MAX-ACCESS read-only
		STATUS current
		DESCRIPTION
		"upsApm160snmp_1018_Branch68LoadRatio stored as 0.01%."
		::= { upsApm160snmpEntry 1018 }
upsApm160snmp_1019_Branch68PowerFactor OBJECT-TYPE
		SYNTAX Integer32
		
		MAX-ACCESS read-only
		STATUS current
		DESCRIPTION
		"upsApm160snmp_1019_Branch68PowerFactor stored as 0.01."
		::= { upsApm160snmpEntry 1019 }
upsApm160snmp_1020_Branch68Voltage OBJECT-TYPE
		SYNTAX Integer32
		
		MAX-ACCESS read-only
		STATUS current
		DESCRIPTION
		"upsApm160snmp_1020_Branch68Voltage stored as 0.01V."
		::= { upsApm160snmpEntry 1020 }
upsApm160snmp_1021_Branch69Current OBJECT-TYPE
		SYNTAX Integer32
		
		MAX-ACCESS read-only
		STATUS current
		DESCRIPTION
		"upsApm160snmp_1021_Branch69Current stored as 0.01A."
		::= { upsApm160snmpEntry 1021 }
upsApm160snmp_1022_Branch69Energy OBJECT-TYPE
		SYNTAX Integer32
		
		MAX-ACCESS read-only
		STATUS current
		DESCRIPTION
		"upsApm160snmp_1022_Branch69Energy stored as 0.01kWh."
		::= { upsApm160snmpEntry 1022 }
upsApm160snmp_1023_Branch69SwitchStatus OBJECT-TYPE
		SYNTAX INTEGER {
			open(0),
			close(1) }
		MAX-ACCESS read-only
		STATUS current
		DESCRIPTION
		"upsApm160snmp_1023_Branch69SwitchStatus status."
		::= { upsApm160snmpEntry 1023 }
upsApm160snmp_1024_Branch69ActivePower OBJECT-TYPE
		SYNTAX Integer32
		
		MAX-ACCESS read-only
		STATUS current
		DESCRIPTION
		"upsApm160snmp_1024_Branch69ActivePower stored as 0.01kW."
		::= { upsApm160snmpEntry 1024 }
upsApm160snmp_1025_Branch69ApparentPower OBJECT-TYPE
		SYNTAX Integer32
		
		MAX-ACCESS read-only
		STATUS current
		DESCRIPTION
		"upsApm160snmp_1025_Branch69ApparentPower stored as 0.01kVA."
		::= { upsApm160snmpEntry 1025 }
upsApm160snmp_1026_Branch69THDi OBJECT-TYPE
		SYNTAX Integer32
		
		MAX-ACCESS read-only
		STATUS current
		DESCRIPTION
		"upsApm160snmp_1026_Branch69THDi stored as 0.01%."
		::= { upsApm160snmpEntry 1026 }
upsApm160snmp_1027_Branch69RatedCurrent OBJECT-TYPE
		SYNTAX Integer32
		
		MAX-ACCESS read-only
		STATUS current
		DESCRIPTION
		"upsApm160snmp_1027_Branch69RatedCurrent stored as 0.01A."
		::= { upsApm160snmpEntry 1027 }
upsApm160snmp_1028_Branch69LoadRatio OBJECT-TYPE
		SYNTAX Integer32
		
		MAX-ACCESS read-only
		STATUS current
		DESCRIPTION
		"upsApm160snmp_1028_Branch69LoadRatio stored as 0.01%."
		::= { upsApm160snmpEntry 1028 }
upsApm160snmp_1029_Branch69PowerFactor OBJECT-TYPE
		SYNTAX Integer32
		
		MAX-ACCESS read-only
		STATUS current
		DESCRIPTION
		"upsApm160snmp_1029_Branch69PowerFactor stored as 0.01."
		::= { upsApm160snmpEntry 1029 }
upsApm160snmp_1030_Branch69Voltage OBJECT-TYPE
		SYNTAX Integer32
		
		MAX-ACCESS read-only
		STATUS current
		DESCRIPTION
		"upsApm160snmp_1030_Branch69Voltage stored as 0.01V."
		::= { upsApm160snmpEntry 1030 }
upsApm160snmp_1031_Branch70Current OBJECT-TYPE
		SYNTAX Integer32
		
		MAX-ACCESS read-only
		STATUS current
		DESCRIPTION
		"upsApm160snmp_1031_Branch70Current stored as 0.01A."
		::= { upsApm160snmpEntry 1031 }
upsApm160snmp_1032_Branch70Energy OBJECT-TYPE
		SYNTAX Integer32
		
		MAX-ACCESS read-only
		STATUS current
		DESCRIPTION
		"upsApm160snmp_1032_Branch70Energy stored as 0.01kWh."
		::= { upsApm160snmpEntry 1032 }
upsApm160snmp_1033_Branch70SwitchStatus OBJECT-TYPE
		SYNTAX INTEGER {
			open(0),
			close(1) }
		MAX-ACCESS read-only
		STATUS current
		DESCRIPTION
		"upsApm160snmp_1033_Branch70SwitchStatus status."
		::= { upsApm160snmpEntry 1033 }
upsApm160snmp_1034_Branch70ActivePower OBJECT-TYPE
		SYNTAX Integer32
		
		MAX-ACCESS read-only
		STATUS current
		DESCRIPTION
		"upsApm160snmp_1034_Branch70ActivePower stored as 0.01kW."
		::= { upsApm160snmpEntry 1034 }
upsApm160snmp_1035_Branch70ApparentPower OBJECT-TYPE
		SYNTAX Integer32
		
		MAX-ACCESS read-only
		STATUS current
		DESCRIPTION
		"upsApm160snmp_1035_Branch70ApparentPower stored as 0.01kVA."
		::= { upsApm160snmpEntry 1035 }
upsApm160snmp_1036_Branch70THDi OBJECT-TYPE
		SYNTAX Integer32
		
		MAX-ACCESS read-only
		STATUS current
		DESCRIPTION
		"upsApm160snmp_1036_Branch70THDi stored as 0.01%."
		::= { upsApm160snmpEntry 1036 }
upsApm160snmp_1037_Branch70RatedCurrent OBJECT-TYPE
		SYNTAX Integer32
		
		MAX-ACCESS read-only
		STATUS current
		DESCRIPTION
		"upsApm160snmp_1037_Branch70RatedCurrent stored as 0.01A."
		::= { upsApm160snmpEntry 1037 }
upsApm160snmp_1038_Branch70LoadRatio OBJECT-TYPE
		SYNTAX Integer32
		
		MAX-ACCESS read-only
		STATUS current
		DESCRIPTION
		"upsApm160snmp_1038_Branch70LoadRatio stored as 0.01%."
		::= { upsApm160snmpEntry 1038 }
upsApm160snmp_1039_Branch70PowerFactor OBJECT-TYPE
		SYNTAX Integer32
		
		MAX-ACCESS read-only
		STATUS current
		DESCRIPTION
		"upsApm160snmp_1039_Branch70PowerFactor stored as 0.01."
		::= { upsApm160snmpEntry 1039 }
upsApm160snmp_1040_Branch70Voltage OBJECT-TYPE
		SYNTAX Integer32
		
		MAX-ACCESS read-only
		STATUS current
		DESCRIPTION
		"upsApm160snmp_1040_Branch70Voltage stored as 0.01V."
		::= { upsApm160snmpEntry 1040 }
upsApm160snmp_1041_Branch71Current OBJECT-TYPE
		SYNTAX Integer32
		
		MAX-ACCESS read-only
		STATUS current
		DESCRIPTION
		"upsApm160snmp_1041_Branch71Current stored as 0.01A."
		::= { upsApm160snmpEntry 1041 }
upsApm160snmp_1042_Branch71Energy OBJECT-TYPE
		SYNTAX Integer32
		
		MAX-ACCESS read-only
		STATUS current
		DESCRIPTION
		"upsApm160snmp_1042_Branch71Energy stored as 0.01kWh."
		::= { upsApm160snmpEntry 1042 }
upsApm160snmp_1043_Branch71SwitchStatus OBJECT-TYPE
		SYNTAX INTEGER {
			open(0),
			close(1) }
		MAX-ACCESS read-only
		STATUS current
		DESCRIPTION
		"upsApm160snmp_1043_Branch71SwitchStatus status."
		::= { upsApm160snmpEntry 1043 }
upsApm160snmp_1044_Branch71ActivePower OBJECT-TYPE
		SYNTAX Integer32
		
		MAX-ACCESS read-only
		STATUS current
		DESCRIPTION
		"upsApm160snmp_1044_Branch71ActivePower stored as 0.01kW."
		::= { upsApm160snmpEntry 1044 }
upsApm160snmp_1045_Branch71ApparentPower OBJECT-TYPE
		SYNTAX Integer32
		
		MAX-ACCESS read-only
		STATUS current
		DESCRIPTION
		"upsApm160snmp_1045_Branch71ApparentPower stored as 0.01kVA."
		::= { upsApm160snmpEntry 1045 }
upsApm160snmp_1046_Branch71THDi OBJECT-TYPE
		SYNTAX Integer32
		
		MAX-ACCESS read-only
		STATUS current
		DESCRIPTION
		"upsApm160snmp_1046_Branch71THDi stored as 0.01%."
		::= { upsApm160snmpEntry 1046 }
upsApm160snmp_1047_Branch71RatedCurrent OBJECT-TYPE
		SYNTAX Integer32
		
		MAX-ACCESS read-only
		STATUS current
		DESCRIPTION
		"upsApm160snmp_1047_Branch71RatedCurrent stored as 0.01A."
		::= { upsApm160snmpEntry 1047 }
upsApm160snmp_1048_Branch71LoadRatio OBJECT-TYPE
		SYNTAX Integer32
		
		MAX-ACCESS read-only
		STATUS current
		DESCRIPTION
		"upsApm160snmp_1048_Branch71LoadRatio stored as 0.01%."
		::= { upsApm160snmpEntry 1048 }
upsApm160snmp_1049_Branch71PowerFactor OBJECT-TYPE
		SYNTAX Integer32
		
		MAX-ACCESS read-only
		STATUS current
		DESCRIPTION
		"upsApm160snmp_1049_Branch71PowerFactor stored as 0.01."
		::= { upsApm160snmpEntry 1049 }
upsApm160snmp_1050_Branch71Voltage OBJECT-TYPE
		SYNTAX Integer32
		
		MAX-ACCESS read-only
		STATUS current
		DESCRIPTION
		"upsApm160snmp_1050_Branch71Voltage stored as 0.01V."
		::= { upsApm160snmpEntry 1050 }
upsApm160snmp_1051_Branch72Current OBJECT-TYPE
		SYNTAX Integer32
		
		MAX-ACCESS read-only
		STATUS current
		DESCRIPTION
		"upsApm160snmp_1051_Branch72Current stored as 0.01A."
		::= { upsApm160snmpEntry 1051 }
upsApm160snmp_1052_Branch72Energy OBJECT-TYPE
		SYNTAX Integer32
		
		MAX-ACCESS read-only
		STATUS current
		DESCRIPTION
		"upsApm160snmp_1052_Branch72Energy stored as 0.01kWh."
		::= { upsApm160snmpEntry 1052 }
upsApm160snmp_1053_Branch72SwitchStatus OBJECT-TYPE
		SYNTAX INTEGER {
			open(0),
			close(1) }
		MAX-ACCESS read-only
		STATUS current
		DESCRIPTION
		"upsApm160snmp_1053_Branch72SwitchStatus status."
		::= { upsApm160snmpEntry 1053 }
upsApm160snmp_1054_Branch72ActivePower OBJECT-TYPE
		SYNTAX Integer32
		
		MAX-ACCESS read-only
		STATUS current
		DESCRIPTION
		"upsApm160snmp_1054_Branch72ActivePower stored as 0.01kW."
		::= { upsApm160snmpEntry 1054 }
upsApm160snmp_1055_Branch72ApparentPower OBJECT-TYPE
		SYNTAX Integer32
		
		MAX-ACCESS read-only
		STATUS current
		DESCRIPTION
		"upsApm160snmp_1055_Branch72ApparentPower stored as 0.01kVA."
		::= { upsApm160snmpEntry 1055 }
upsApm160snmp_1056_Branch72THDi OBJECT-TYPE
		SYNTAX Integer32
		
		MAX-ACCESS read-only
		STATUS current
		DESCRIPTION
		"upsApm160snmp_1056_Branch72THDi stored as 0.01%."
		::= { upsApm160snmpEntry 1056 }
upsApm160snmp_1057_Branch72RatedCurrent OBJECT-TYPE
		SYNTAX Integer32
		
		MAX-ACCESS read-only
		STATUS current
		DESCRIPTION
		"upsApm160snmp_1057_Branch72RatedCurrent stored as 0.01A."
		::= { upsApm160snmpEntry 1057 }
upsApm160snmp_1058_Branch72LoadRatio OBJECT-TYPE
		SYNTAX Integer32
		
		MAX-ACCESS read-only
		STATUS current
		DESCRIPTION
		"upsApm160snmp_1058_Branch72LoadRatio stored as 0.01%."
		::= { upsApm160snmpEntry 1058 }
upsApm160snmp_1059_Branch72PowerFactor OBJECT-TYPE
		SYNTAX Integer32
		
		MAX-ACCESS read-only
		STATUS current
		DESCRIPTION
		"upsApm160snmp_1059_Branch72PowerFactor stored as 0.01."
		::= { upsApm160snmpEntry 1059 }
upsApm160snmp_1060_Branch72Voltage OBJECT-TYPE
		SYNTAX Integer32
		
		MAX-ACCESS read-only
		STATUS current
		DESCRIPTION
		"upsApm160snmp_1060_Branch72Voltage stored as 0.01V."
		::= { upsApm160snmpEntry 1060 }
upsApm160snmp_1061_InputSource1CurrentA OBJECT-TYPE
		SYNTAX Integer32
		
		MAX-ACCESS read-only
		STATUS current
		DESCRIPTION
		"upsApm160snmp_1061_InputSource1CurrentA stored as 0.01A."
		::= { upsApm160snmpEntry 1061 }
upsApm160snmp_1062_InputSource1CurrentB OBJECT-TYPE
		SYNTAX Integer32
		
		MAX-ACCESS read-only
		STATUS current
		DESCRIPTION
		"upsApm160snmp_1062_InputSource1CurrentB stored as 0.01A."
		::= { upsApm160snmpEntry 1062 }
upsApm160snmp_1063_InputSource1CurrentC OBJECT-TYPE
		SYNTAX Integer32
		
		MAX-ACCESS read-only
		STATUS current
		DESCRIPTION
		"upsApm160snmp_1063_InputSource1CurrentC stored as 0.01A."
		::= { upsApm160snmpEntry 1063 }
upsApm160snmp_1064_InputSource1EnergyA OBJECT-TYPE
		SYNTAX Integer32
		
		MAX-ACCESS read-only
		STATUS current
		DESCRIPTION
		"upsApm160snmp_1064_InputSource1EnergyA stored as 0.01kWh."
		::= { upsApm160snmpEntry 1064 }
upsApm160snmp_1065_InputSource1EnergyB OBJECT-TYPE
		SYNTAX Integer32
		
		MAX-ACCESS read-only
		STATUS current
		DESCRIPTION
		"upsApm160snmp_1065_InputSource1EnergyB stored as 0.01kWh."
		::= { upsApm160snmpEntry 1065 }
upsApm160snmp_1066_InputSource1EnergyC OBJECT-TYPE
		SYNTAX Integer32
		
		MAX-ACCESS read-only
		STATUS current
		DESCRIPTION
		"upsApm160snmp_1066_InputSource1EnergyC stored as 0.01kWh."
		::= { upsApm160snmpEntry 1066 }
upsApm160snmp_1067_InputSource1SwitchStatusA OBJECT-TYPE
		SYNTAX INTEGER {
			open(0),
			close(1) }
		MAX-ACCESS read-only
		STATUS current
		DESCRIPTION
		"upsApm160snmp_1067_InputSource1SwitchStatusA status."
		::= { upsApm160snmpEntry 1067 }
upsApm160snmp_1068_InputSource1SwitchStatusB OBJECT-TYPE
		SYNTAX INTEGER {
			open(0),
			close(1) }
		MAX-ACCESS read-only
		STATUS current
		DESCRIPTION
		"upsApm160snmp_1068_InputSource1SwitchStatusB status."
		::= { upsApm160snmpEntry 1068 }
upsApm160snmp_1069_InputSource1SwitchStatusC OBJECT-TYPE
		SYNTAX INTEGER {
			open(0),
			close(1) }
		MAX-ACCESS read-only
		STATUS current
		DESCRIPTION
		"upsApm160snmp_1069_InputSource1SwitchStatusC status."
		::= { upsApm160snmpEntry 1069 }
upsApm160snmp_1070_InputSource1ActivePowerA OBJECT-TYPE
		SYNTAX Integer32
		
		MAX-ACCESS read-only
		STATUS current
		DESCRIPTION
		"upsApm160snmp_1070_InputSource1ActivePowerA stored as 0.01kW."
		::= { upsApm160snmpEntry 1070 }
upsApm160snmp_1071_InputSource1ActivePowerB OBJECT-TYPE
		SYNTAX Integer32
		
		MAX-ACCESS read-only
		STATUS current
		DESCRIPTION
		"upsApm160snmp_1071_InputSource1ActivePowerB stored as 0.01kW."
		::= { upsApm160snmpEntry 1071 }
upsApm160snmp_1072_InputSource1ActivePowerC OBJECT-TYPE
		SYNTAX Integer32
		
		MAX-ACCESS read-only
		STATUS current
		DESCRIPTION
		"upsApm160snmp_1072_InputSource1ActivePowerC stored as 0.01kW."
		::= { upsApm160snmpEntry 1072 }
upsApm160snmp_1073_InputSource1ApparentPowerA OBJECT-TYPE
		SYNTAX Integer32
		
		MAX-ACCESS read-only
		STATUS current
		DESCRIPTION
		"upsApm160snmp_1073_InputSource1ApparentPowerA stored as 0.01kVA."
		::= { upsApm160snmpEntry 1073 }
upsApm160snmp_1074_InputSource1ApparentPowerB OBJECT-TYPE
		SYNTAX Integer32
		
		MAX-ACCESS read-only
		STATUS current
		DESCRIPTION
		"upsApm160snmp_1074_InputSource1ApparentPowerB stored as 0.01kVA."
		::= { upsApm160snmpEntry 1074 }
upsApm160snmp_1075_InputSource1ApparentPowerC OBJECT-TYPE
		SYNTAX Integer32
		
		MAX-ACCESS read-only
		STATUS current
		DESCRIPTION
		"upsApm160snmp_1075_InputSource1ApparentPowerC stored as 0.01kVA."
		::= { upsApm160snmpEntry 1075 }
upsApm160snmp_1076_InputSource1THDiA OBJECT-TYPE
		SYNTAX Integer32
		
		MAX-ACCESS read-only
		STATUS current
		DESCRIPTION
		"upsApm160snmp_1076_InputSource1THDiA stored as 0.01%."
		::= { upsApm160snmpEntry 1076 }
upsApm160snmp_1077_InputSource1THDiB OBJECT-TYPE
		SYNTAX Integer32
		
		MAX-ACCESS read-only
		STATUS current
		DESCRIPTION
		"upsApm160snmp_1077_InputSource1THDiB stored as 0.01%."
		::= { upsApm160snmpEntry 1077 }
upsApm160snmp_1078_InputSource1THDiC OBJECT-TYPE
		SYNTAX Integer32
		
		MAX-ACCESS read-only
		STATUS current
		DESCRIPTION
		"upsApm160snmp_1078_InputSource1THDiC stored as 0.01%."
		::= { upsApm160snmpEntry 1078 }
upsApm160snmp_1079_InputSource1RatedCurrentA OBJECT-TYPE
		SYNTAX Integer32
		
		MAX-ACCESS read-only
		STATUS current
		DESCRIPTION
		"upsApm160snmp_1079_InputSource1RatedCurrentA stored as 0.01A."
		::= { upsApm160snmpEntry 1079 }
upsApm160snmp_1080_InputSource1RatedCurrentB OBJECT-TYPE
		SYNTAX Integer32
		
		MAX-ACCESS read-only
		STATUS current
		DESCRIPTION
		"upsApm160snmp_1080_InputSource1RatedCurrentB stored as 0.01A."
		::= { upsApm160snmpEntry 1080 }
upsApm160snmp_1081_InputSource1RatedCurrentC OBJECT-TYPE
		SYNTAX Integer32
		
		MAX-ACCESS read-only
		STATUS current
		DESCRIPTION
		"upsApm160snmp_1081_InputSource1RatedCurrentC stored as 0.01A."
		::= { upsApm160snmpEntry 1081 }
upsApm160snmp_1082_InputSource1LoadRatioA OBJECT-TYPE
		SYNTAX Integer32
		
		MAX-ACCESS read-only
		STATUS current
		DESCRIPTION
		"upsApm160snmp_1082_InputSource1LoadRatioA stored as 0.01%."
		::= { upsApm160snmpEntry 1082 }
upsApm160snmp_1083_InputSource1LoadRatioB OBJECT-TYPE
		SYNTAX Integer32
		
		MAX-ACCESS read-only
		STATUS current
		DESCRIPTION
		"upsApm160snmp_1083_InputSource1LoadRatioB stored as 0.01%."
		::= { upsApm160snmpEntry 1083 }
upsApm160snmp_1084_InputSource1LoadRatioC OBJECT-TYPE
		SYNTAX Integer32
		
		MAX-ACCESS read-only
		STATUS current
		DESCRIPTION
		"upsApm160snmp_1084_InputSource1LoadRatioC stored as 0.01%."
		::= { upsApm160snmpEntry 1084 }
upsApm160snmp_1085_InputSource1PowerFactorA OBJECT-TYPE
		SYNTAX Integer32
		
		MAX-ACCESS read-only
		STATUS current
		DESCRIPTION
		"upsApm160snmp_1085_InputSource1PowerFactorA stored as 0.01."
		::= { upsApm160snmpEntry 1085 }
upsApm160snmp_1086_InputSource1PowerFactorB OBJECT-TYPE
		SYNTAX Integer32
		
		MAX-ACCESS read-only
		STATUS current
		DESCRIPTION
		"upsApm160snmp_1086_InputSource1PowerFactorB stored as 0.01."
		::= { upsApm160snmpEntry 1086 }
upsApm160snmp_1087_InputSource1PowerFactorC OBJECT-TYPE
		SYNTAX Integer32
		
		MAX-ACCESS read-only
		STATUS current
		DESCRIPTION
		"upsApm160snmp_1087_InputSource1PowerFactorC stored as 0.01."
		::= { upsApm160snmpEntry 1087 }
upsApm160snmp_1088_InputSource1LineVoltageA OBJECT-TYPE
		SYNTAX Integer32
		
		MAX-ACCESS read-only
		STATUS current
		DESCRIPTION
		"upsApm160snmp_1088_InputSource1LineVoltageA stored as 0.01V."
		::= { upsApm160snmpEntry 1088 }
upsApm160snmp_1089_InputSource1LineVoltageB OBJECT-TYPE
		SYNTAX Integer32
		
		MAX-ACCESS read-only
		STATUS current
		DESCRIPTION
		"upsApm160snmp_1089_InputSource1LineVoltageB stored as 0.01V."
		::= { upsApm160snmpEntry 1089 }
upsApm160snmp_1090_InputSource1LineVoltageC OBJECT-TYPE
		SYNTAX Integer32
		
		MAX-ACCESS read-only
		STATUS current
		DESCRIPTION
		"upsApm160snmp_1090_InputSource1LineVoltageC stored as 0.01V."
		::= { upsApm160snmpEntry 1090 }
upsApm160snmp_1091_InputSource1PhaseVoltageA OBJECT-TYPE
		SYNTAX Integer32
		
		MAX-ACCESS read-only
		STATUS current
		DESCRIPTION
		"upsApm160snmp_1091_InputSource1PhaseVoltageA stored as 0.01V."
		::= { upsApm160snmpEntry 1091 }
upsApm160snmp_1092_InputSource1PhaseVoltageB OBJECT-TYPE
		SYNTAX Integer32
		
		MAX-ACCESS read-only
		STATUS current
		DESCRIPTION
		"upsApm160snmp_1092_InputSource1PhaseVoltageB stored as 0.01V."
		::= { upsApm160snmpEntry 1092 }
upsApm160snmp_1093_InputSource1PhaseVoltageC OBJECT-TYPE
		SYNTAX Integer32
		
		MAX-ACCESS read-only
		STATUS current
		DESCRIPTION
		"upsApm160snmp_1093_InputSource1PhaseVoltageC stored as 0.01V."
		::= { upsApm160snmpEntry 1093 }
upsApm160snmp_1094_InputSource1FrequencyA OBJECT-TYPE
		SYNTAX Integer32
		
		MAX-ACCESS read-only
		STATUS current
		DESCRIPTION
		"upsApm160snmp_1094_InputSource1FrequencyA stored as 0.01Hz."
		::= { upsApm160snmpEntry 1094 }
upsApm160snmp_1095_InputSource1FrequencyB OBJECT-TYPE
		SYNTAX Integer32
		
		MAX-ACCESS read-only
		STATUS current
		DESCRIPTION
		"upsApm160snmp_1095_InputSource1FrequencyB stored as 0.01Hz."
		::= { upsApm160snmpEntry 1095 }
upsApm160snmp_1096_InputSource1FrequencyC OBJECT-TYPE
		SYNTAX Integer32
		
		MAX-ACCESS read-only
		STATUS current
		DESCRIPTION
		"upsApm160snmp_1096_InputSource1FrequencyC stored as 0.01Hz."
		::= { upsApm160snmpEntry 1096 }
upsApm160snmp_1097_InputSource1THDuA OBJECT-TYPE
		SYNTAX Integer32
		
		MAX-ACCESS read-only
		STATUS current
		DESCRIPTION
		"upsApm160snmp_1097_InputSource1THDuA stored as 0.01%."
		::= { upsApm160snmpEntry 1097 }
upsApm160snmp_1098_InputSource1THDuB OBJECT-TYPE
		SYNTAX Integer32
		
		MAX-ACCESS read-only
		STATUS current
		DESCRIPTION
		"upsApm160snmp_1098_InputSource1THDuB stored as 0.01%."
		::= { upsApm160snmpEntry 1098 }
upsApm160snmp_1099_InputSource1THDuC OBJECT-TYPE
		SYNTAX Integer32
		
		MAX-ACCESS read-only
		STATUS current
		DESCRIPTION
		"upsApm160snmp_1099_InputSource1THDuC stored as 0.01%."
		::= { upsApm160snmpEntry 1099 }
upsApm160snmp_1100_InputSource2CurrentA OBJECT-TYPE
		SYNTAX Integer32
		
		MAX-ACCESS read-only
		STATUS current
		DESCRIPTION
		"upsApm160snmp_1100_InputSource2CurrentA stored as 0.01A."
		::= { upsApm160snmpEntry 1100 }
upsApm160snmp_1101_InputSource2CurrentB OBJECT-TYPE
		SYNTAX Integer32
		
		MAX-ACCESS read-only
		STATUS current
		DESCRIPTION
		"upsApm160snmp_1101_InputSource2CurrentB stored as 0.01A."
		::= { upsApm160snmpEntry 1101 }
upsApm160snmp_1102_InputSource2CurrentC OBJECT-TYPE
		SYNTAX Integer32
		
		MAX-ACCESS read-only
		STATUS current
		DESCRIPTION
		"upsApm160snmp_1102_InputSource2CurrentC stored as 0.01A."
		::= { upsApm160snmpEntry 1102 }
upsApm160snmp_1103_InputSource2EnergyA OBJECT-TYPE
		SYNTAX Integer32
		
		MAX-ACCESS read-only
		STATUS current
		DESCRIPTION
		"upsApm160snmp_1103_InputSource2EnergyA stored as 0.01kWh."
		::= { upsApm160snmpEntry 1103 }
upsApm160snmp_1104_InputSource2EnergyB OBJECT-TYPE
		SYNTAX Integer32
		
		MAX-ACCESS read-only
		STATUS current
		DESCRIPTION
		"upsApm160snmp_1104_InputSource2EnergyB stored as 0.01kWh."
		::= { upsApm160snmpEntry 1104 }
upsApm160snmp_1105_InputSource2EnergyC OBJECT-TYPE
		SYNTAX Integer32
		
		MAX-ACCESS read-only
		STATUS current
		DESCRIPTION
		"upsApm160snmp_1105_InputSource2EnergyC stored as 0.01kWh."
		::= { upsApm160snmpEntry 1105 }
upsApm160snmp_1106_InputSource2SwitchStatusA OBJECT-TYPE
		SYNTAX INTEGER {
			open(0),
			close(1) }
		MAX-ACCESS read-only
		STATUS current
		DESCRIPTION
		"upsApm160snmp_1106_InputSource2SwitchStatusA status."
		::= { upsApm160snmpEntry 1106 }
upsApm160snmp_1107_InputSource2SwitchStatusB OBJECT-TYPE
		SYNTAX INTEGER {
			open(0),
			close(1) }
		MAX-ACCESS read-only
		STATUS current
		DESCRIPTION
		"upsApm160snmp_1107_InputSource2SwitchStatusB status."
		::= { upsApm160snmpEntry 1107 }
upsApm160snmp_1108_InputSource2SwitchStatusC OBJECT-TYPE
		SYNTAX INTEGER {
			open(0),
			close(1) }
		MAX-ACCESS read-only
		STATUS current
		DESCRIPTION
		"upsApm160snmp_1108_InputSource2SwitchStatusC status."
		::= { upsApm160snmpEntry 1108 }
upsApm160snmp_1109_InputSource2ActivePowerA OBJECT-TYPE
		SYNTAX Integer32
		
		MAX-ACCESS read-only
		STATUS current
		DESCRIPTION
		"upsApm160snmp_1109_InputSource2ActivePowerA stored as 0.01kW."
		::= { upsApm160snmpEntry 1109 }
upsApm160snmp_1110_InputSource2ActivePowerB OBJECT-TYPE
		SYNTAX Integer32
		
		MAX-ACCESS read-only
		STATUS current
		DESCRIPTION
		"upsApm160snmp_1110_InputSource2ActivePowerB stored as 0.01kW."
		::= { upsApm160snmpEntry 1110 }
upsApm160snmp_1111_InputSource2ActivePowerC OBJECT-TYPE
		SYNTAX Integer32
		
		MAX-ACCESS read-only
		STATUS current
		DESCRIPTION
		"upsApm160snmp_1111_InputSource2ActivePowerC stored as 0.01kW."
		::= { upsApm160snmpEntry 1111 }
upsApm160snmp_1112_InputSource2ApparentPowerA OBJECT-TYPE
		SYNTAX Integer32
		
		MAX-ACCESS read-only
		STATUS current
		DESCRIPTION
		"upsApm160snmp_1112_InputSource2ApparentPowerA stored as 0.01kVA."
		::= { upsApm160snmpEntry 1112 }
upsApm160snmp_1113_InputSource2ApparentPowerB OBJECT-TYPE
		SYNTAX Integer32
		
		MAX-ACCESS read-only
		STATUS current
		DESCRIPTION
		"upsApm160snmp_1113_InputSource2ApparentPowerB stored as 0.01kVA."
		::= { upsApm160snmpEntry 1113 }
upsApm160snmp_1114_InputSource2ApparentPowerC OBJECT-TYPE
		SYNTAX Integer32
		
		MAX-ACCESS read-only
		STATUS current
		DESCRIPTION
		"upsApm160snmp_1114_InputSource2ApparentPowerC stored as 0.01kVA."
		::= { upsApm160snmpEntry 1114 }
upsApm160snmp_1115_InputSource2THDiA OBJECT-TYPE
		SYNTAX Integer32
		
		MAX-ACCESS read-only
		STATUS current
		DESCRIPTION
		"upsApm160snmp_1115_InputSource2THDiA stored as 0.01%."
		::= { upsApm160snmpEntry 1115 }
upsApm160snmp_1116_InputSource2THDiB OBJECT-TYPE
		SYNTAX Integer32
		
		MAX-ACCESS read-only
		STATUS current
		DESCRIPTION
		"upsApm160snmp_1116_InputSource2THDiB stored as 0.01%."
		::= { upsApm160snmpEntry 1116 }
upsApm160snmp_1117_InputSource2THDiC OBJECT-TYPE
		SYNTAX Integer32
		
		MAX-ACCESS read-only
		STATUS current
		DESCRIPTION
		"upsApm160snmp_1117_InputSource2THDiC stored as 0.01%."
		::= { upsApm160snmpEntry 1117 }
upsApm160snmp_1118_InputSource2RatedCurrentA OBJECT-TYPE
		SYNTAX Integer32
		
		MAX-ACCESS read-only
		STATUS current
		DESCRIPTION
		"upsApm160snmp_1118_InputSource2RatedCurrentA stored as 0.01A."
		::= { upsApm160snmpEntry 1118 }
upsApm160snmp_1119_InputSource2RatedCurrentB OBJECT-TYPE
		SYNTAX Integer32
		
		MAX-ACCESS read-only
		STATUS current
		DESCRIPTION
		"upsApm160snmp_1119_InputSource2RatedCurrentB stored as 0.01A."
		::= { upsApm160snmpEntry 1119 }
upsApm160snmp_1120_InputSource2RatedCurrentC OBJECT-TYPE
		SYNTAX Integer32
		
		MAX-ACCESS read-only
		STATUS current
		DESCRIPTION
		"upsApm160snmp_1120_InputSource2RatedCurrentC stored as 0.01A."
		::= { upsApm160snmpEntry 1120 }
upsApm160snmp_1121_InputSource2LoadRatioA OBJECT-TYPE
		SYNTAX Integer32
		
		MAX-ACCESS read-only
		STATUS current
		DESCRIPTION
		"upsApm160snmp_1121_InputSource2LoadRatioA stored as 0.01%."
		::= { upsApm160snmpEntry 1121 }
upsApm160snmp_1122_InputSource2LoadRatioB OBJECT-TYPE
		SYNTAX Integer32
		
		MAX-ACCESS read-only
		STATUS current
		DESCRIPTION
		"upsApm160snmp_1122_InputSource2LoadRatioB stored as 0.01%."
		::= { upsApm160snmpEntry 1122 }
upsApm160snmp_1123_InputSource2LoadRatioC OBJECT-TYPE
		SYNTAX Integer32
		
		MAX-ACCESS read-only
		STATUS current
		DESCRIPTION
		"upsApm160snmp_1123_InputSource2LoadRatioC stored as 0.01%."
		::= { upsApm160snmpEntry 1123 }
upsApm160snmp_1124_InputSource2PowerFactorA OBJECT-TYPE
		SYNTAX Integer32
		
		MAX-ACCESS read-only
		STATUS current
		DESCRIPTION
		"upsApm160snmp_1124_InputSource2PowerFactorA stored as 0.01."
		::= { upsApm160snmpEntry 1124 }
upsApm160snmp_1125_InputSource2PowerFactorB OBJECT-TYPE
		SYNTAX Integer32
		
		MAX-ACCESS read-only
		STATUS current
		DESCRIPTION
		"upsApm160snmp_1125_InputSource2PowerFactorB stored as 0.01."
		::= { upsApm160snmpEntry 1125 }
upsApm160snmp_1126_InputSource2PowerFactorC OBJECT-TYPE
		SYNTAX Integer32
		
		MAX-ACCESS read-only
		STATUS current
		DESCRIPTION
		"upsApm160snmp_1126_InputSource2PowerFactorC stored as 0.01."
		::= { upsApm160snmpEntry 1126 }
upsApm160snmp_1127_InputSource2LineVoltageA OBJECT-TYPE
		SYNTAX Integer32
		
		MAX-ACCESS read-only
		STATUS current
		DESCRIPTION
		"upsApm160snmp_1127_InputSource2LineVoltageA stored as 0.01V."
		::= { upsApm160snmpEntry 1127 }
upsApm160snmp_1128_InputSource2LineVoltageB OBJECT-TYPE
		SYNTAX Integer32
		
		MAX-ACCESS read-only
		STATUS current
		DESCRIPTION
		"upsApm160snmp_1128_InputSource2LineVoltageB stored as 0.01V."
		::= { upsApm160snmpEntry 1128 }
upsApm160snmp_1129_InputSource2LineVoltageC OBJECT-TYPE
		SYNTAX Integer32
		
		MAX-ACCESS read-only
		STATUS current
		DESCRIPTION
		"upsApm160snmp_1129_InputSource2LineVoltageC stored as 0.01V."
		::= { upsApm160snmpEntry 1129 }
upsApm160snmp_1130_InputSource2PhaseVoltageA OBJECT-TYPE
		SYNTAX Integer32
		
		MAX-ACCESS read-only
		STATUS current
		DESCRIPTION
		"upsApm160snmp_1130_InputSource2PhaseVoltageA stored as 0.01V."
		::= { upsApm160snmpEntry 1130 }
upsApm160snmp_1131_InputSource2PhaseVoltageB OBJECT-TYPE
		SYNTAX Integer32
		
		MAX-ACCESS read-only
		STATUS current
		DESCRIPTION
		"upsApm160snmp_1131_InputSource2PhaseVoltageB stored as 0.01V."
		::= { upsApm160snmpEntry 1131 }
upsApm160snmp_1132_InputSource2PhaseVoltageC OBJECT-TYPE
		SYNTAX Integer32
		
		MAX-ACCESS read-only
		STATUS current
		DESCRIPTION
		"upsApm160snmp_1132_InputSource2PhaseVoltageC stored as 0.01V."
		::= { upsApm160snmpEntry 1132 }
upsApm160snmp_1133_InputSource2FrequencyA OBJECT-TYPE
		SYNTAX Integer32
		
		MAX-ACCESS read-only
		STATUS current
		DESCRIPTION
		"upsApm160snmp_1133_InputSource2FrequencyA stored as 0.01Hz."
		::= { upsApm160snmpEntry 1133 }
upsApm160snmp_1134_InputSource2FrequencyB OBJECT-TYPE
		SYNTAX Integer32
		
		MAX-ACCESS read-only
		STATUS current
		DESCRIPTION
		"upsApm160snmp_1134_InputSource2FrequencyB stored as 0.01Hz."
		::= { upsApm160snmpEntry 1134 }
upsApm160snmp_1135_InputSource2FrequencyC OBJECT-TYPE
		SYNTAX Integer32
		
		MAX-ACCESS read-only
		STATUS current
		DESCRIPTION
		"upsApm160snmp_1135_InputSource2FrequencyC stored as 0.01Hz."
		::= { upsApm160snmpEntry 1135 }
upsApm160snmp_1136_InputSource2THDuA OBJECT-TYPE
		SYNTAX Integer32
		
		MAX-ACCESS read-only
		STATUS current
		DESCRIPTION
		"upsApm160snmp_1136_InputSource2THDuA stored as 0.01%."
		::= { upsApm160snmpEntry 1136 }
upsApm160snmp_1137_InputSource2THDuB OBJECT-TYPE
		SYNTAX Integer32
		
		MAX-ACCESS read-only
		STATUS current
		DESCRIPTION
		"upsApm160snmp_1137_InputSource2THDuB stored as 0.01%."
		::= { upsApm160snmpEntry 1137 }
upsApm160snmp_1138_InputSource2THDuC OBJECT-TYPE
		SYNTAX Integer32
		
		MAX-ACCESS read-only
		STATUS current
		DESCRIPTION
		"upsApm160snmp_1138_InputSource2THDuC stored as 0.01%."
		::= { upsApm160snmpEntry 1138 }
upsApm160snmp_1139_OnputSource1CurrentA OBJECT-TYPE
		SYNTAX Integer32
		
		MAX-ACCESS read-only
		STATUS current
		DESCRIPTION
		"upsApm160snmp_1139_OnputSource1CurrentA stored as 0.01A."
		::= { upsApm160snmpEntry 1139 }
upsApm160snmp_1140_OnputSource1CurrentB OBJECT-TYPE
		SYNTAX Integer32
		
		MAX-ACCESS read-only
		STATUS current
		DESCRIPTION
		"upsApm160snmp_1140_OnputSource1CurrentB stored as 0.01A."
		::= { upsApm160snmpEntry 1140 }
upsApm160snmp_1141_OnputSource1CurrentC OBJECT-TYPE
		SYNTAX Integer32
		
		MAX-ACCESS read-only
		STATUS current
		DESCRIPTION
		"upsApm160snmp_1141_OnputSource1CurrentC stored as 0.01A."
		::= { upsApm160snmpEntry 1141 }
upsApm160snmp_1142_OnputSource1EnergyA OBJECT-TYPE
		SYNTAX Integer32
		
		MAX-ACCESS read-only
		STATUS current
		DESCRIPTION
		"upsApm160snmp_1142_OnputSource1EnergyA stored as 0.01kWh."
		::= { upsApm160snmpEntry 1142 }
upsApm160snmp_1143_OnputSource1EnergyB OBJECT-TYPE
		SYNTAX Integer32
		
		MAX-ACCESS read-only
		STATUS current
		DESCRIPTION
		"upsApm160snmp_1143_OnputSource1EnergyB stored as 0.01kWh."
		::= { upsApm160snmpEntry 1143 }
upsApm160snmp_1144_OnputSource1EnergyC OBJECT-TYPE
		SYNTAX Integer32
		
		MAX-ACCESS read-only
		STATUS current
		DESCRIPTION
		"upsApm160snmp_1144_OnputSource1EnergyC stored as 0.01kWh."
		::= { upsApm160snmpEntry 1144 }
upsApm160snmp_1145_OnputSource1SwitchStatusA OBJECT-TYPE
		SYNTAX INTEGER {
			open(0),
			close(1) }
		MAX-ACCESS read-only
		STATUS current
		DESCRIPTION
		"upsApm160snmp_1145_OnputSource1SwitchStatusA status."
		::= { upsApm160snmpEntry 1145 }
upsApm160snmp_1146_OnputSource1SwitchStatusB OBJECT-TYPE
		SYNTAX INTEGER {
			open(0),
			close(1) }
		MAX-ACCESS read-only
		STATUS current
		DESCRIPTION
		"upsApm160snmp_1146_OnputSource1SwitchStatusB status."
		::= { upsApm160snmpEntry 1146 }
upsApm160snmp_1147_OnputSource1SwitchStatusC OBJECT-TYPE
		SYNTAX INTEGER {
			open(0),
			close(1) }
		MAX-ACCESS read-only
		STATUS current
		DESCRIPTION
		"upsApm160snmp_1147_OnputSource1SwitchStatusC status."
		::= { upsApm160snmpEntry 1147 }
upsApm160snmp_1148_OnputSource1ActivePowerA OBJECT-TYPE
		SYNTAX Integer32
		
		MAX-ACCESS read-only
		STATUS current
		DESCRIPTION
		"upsApm160snmp_1148_OnputSource1ActivePowerA stored as 0.01kW."
		::= { upsApm160snmpEntry 1148 }
upsApm160snmp_1149_OnputSource1ActivePowerB OBJECT-TYPE
		SYNTAX Integer32
		
		MAX-ACCESS read-only
		STATUS current
		DESCRIPTION
		"upsApm160snmp_1149_OnputSource1ActivePowerB stored as 0.01kW."
		::= { upsApm160snmpEntry 1149 }
upsApm160snmp_1150_OnputSource1ActivePowerC OBJECT-TYPE
		SYNTAX Integer32
		
		MAX-ACCESS read-only
		STATUS current
		DESCRIPTION
		"upsApm160snmp_1150_OnputSource1ActivePowerC stored as 0.01kW."
		::= { upsApm160snmpEntry 1150 }
upsApm160snmp_1151_OnputSource1ApparentPowerA OBJECT-TYPE
		SYNTAX Integer32
		
		MAX-ACCESS read-only
		STATUS current
		DESCRIPTION
		"upsApm160snmp_1151_OnputSource1ApparentPowerA stored as 0.01kVA."
		::= { upsApm160snmpEntry 1151 }
upsApm160snmp_1152_OnputSource1ApparentPowerB OBJECT-TYPE
		SYNTAX Integer32
		
		MAX-ACCESS read-only
		STATUS current
		DESCRIPTION
		"upsApm160snmp_1152_OnputSource1ApparentPowerB stored as 0.01kVA."
		::= { upsApm160snmpEntry 1152 }
upsApm160snmp_1153_OnputSource1ApparentPowerC OBJECT-TYPE
		SYNTAX Integer32
		
		MAX-ACCESS read-only
		STATUS current
		DESCRIPTION
		"upsApm160snmp_1153_OnputSource1ApparentPowerC stored as 0.01kVA."
		::= { upsApm160snmpEntry 1153 }
upsApm160snmp_1154_OnputSource1THDiA OBJECT-TYPE
		SYNTAX Integer32
		
		MAX-ACCESS read-only
		STATUS current
		DESCRIPTION
		"upsApm160snmp_1154_OnputSource1THDiA stored as 0.01%."
		::= { upsApm160snmpEntry 1154 }
upsApm160snmp_1155_OnputSource1THDiB OBJECT-TYPE
		SYNTAX Integer32
		
		MAX-ACCESS read-only
		STATUS current
		DESCRIPTION
		"upsApm160snmp_1155_OnputSource1THDiB stored as 0.01%."
		::= { upsApm160snmpEntry 1155 }
upsApm160snmp_1156_OnputSource1THDiC OBJECT-TYPE
		SYNTAX Integer32
		
		MAX-ACCESS read-only
		STATUS current
		DESCRIPTION
		"upsApm160snmp_1156_OnputSource1THDiC stored as 0.01%."
		::= { upsApm160snmpEntry 1156 }
upsApm160snmp_1157_OnputSource1RatedCurrentA OBJECT-TYPE
		SYNTAX Integer32
		
		MAX-ACCESS read-only
		STATUS current
		DESCRIPTION
		"upsApm160snmp_1157_OnputSource1RatedCurrentA stored as 0.01A."
		::= { upsApm160snmpEntry 1157 }
upsApm160snmp_1158_OnputSource1RatedCurrentB OBJECT-TYPE
		SYNTAX Integer32
		
		MAX-ACCESS read-only
		STATUS current
		DESCRIPTION
		"upsApm160snmp_1158_OnputSource1RatedCurrentB stored as 0.01A."
		::= { upsApm160snmpEntry 1158 }
upsApm160snmp_1159_OnputSource1RatedCurrentC OBJECT-TYPE
		SYNTAX Integer32
		
		MAX-ACCESS read-only
		STATUS current
		DESCRIPTION
		"upsApm160snmp_1159_OnputSource1RatedCurrentC stored as 0.01A."
		::= { upsApm160snmpEntry 1159 }
upsApm160snmp_1160_OnputSource1LoadRatioA OBJECT-TYPE
		SYNTAX Integer32
		
		MAX-ACCESS read-only
		STATUS current
		DESCRIPTION
		"upsApm160snmp_1160_OnputSource1LoadRatioA stored as 0.01%."
		::= { upsApm160snmpEntry 1160 }
upsApm160snmp_1161_OnputSource1LoadRatioB OBJECT-TYPE
		SYNTAX Integer32
		
		MAX-ACCESS read-only
		STATUS current
		DESCRIPTION
		"upsApm160snmp_1161_OnputSource1LoadRatioB stored as 0.01%."
		::= { upsApm160snmpEntry 1161 }
upsApm160snmp_1162_OnputSource1LoadRatioC OBJECT-TYPE
		SYNTAX Integer32
		
		MAX-ACCESS read-only
		STATUS current
		DESCRIPTION
		"upsApm160snmp_1162_OnputSource1LoadRatioC stored as 0.01%."
		::= { upsApm160snmpEntry 1162 }
upsApm160snmp_1163_OnputSource1PowerFactorA OBJECT-TYPE
		SYNTAX Integer32
		
		MAX-ACCESS read-only
		STATUS current
		DESCRIPTION
		"upsApm160snmp_1163_OnputSource1PowerFactorA stored as 0.01."
		::= { upsApm160snmpEntry 1163 }
upsApm160snmp_1164_OnputSource1PowerFactorB OBJECT-TYPE
		SYNTAX Integer32
		
		MAX-ACCESS read-only
		STATUS current
		DESCRIPTION
		"upsApm160snmp_1164_OnputSource1PowerFactorB stored as 0.01."
		::= { upsApm160snmpEntry 1164 }
upsApm160snmp_1165_OnputSource1PowerFactorC OBJECT-TYPE
		SYNTAX Integer32
		
		MAX-ACCESS read-only
		STATUS current
		DESCRIPTION
		"upsApm160snmp_1165_OnputSource1PowerFactorC stored as 0.01."
		::= { upsApm160snmpEntry 1165 }
upsApm160snmp_1166_OnputSource1LineVoltageA OBJECT-TYPE
		SYNTAX Integer32
		
		MAX-ACCESS read-only
		STATUS current
		DESCRIPTION
		"upsApm160snmp_1166_OnputSource1LineVoltageA stored as 0.01V."
		::= { upsApm160snmpEntry 1166 }
upsApm160snmp_1167_OnputSource1LineVoltageB OBJECT-TYPE
		SYNTAX Integer32
		
		MAX-ACCESS read-only
		STATUS current
		DESCRIPTION
		"upsApm160snmp_1167_OnputSource1LineVoltageB stored as 0.01V."
		::= { upsApm160snmpEntry 1167 }
upsApm160snmp_1168_OnputSource1LineVoltageC OBJECT-TYPE
		SYNTAX Integer32
		
		MAX-ACCESS read-only
		STATUS current
		DESCRIPTION
		"upsApm160snmp_1168_OnputSource1LineVoltageC stored as 0.01V."
		::= { upsApm160snmpEntry 1168 }
upsApm160snmp_1169_OnputSource1PhaseVoltageA OBJECT-TYPE
		SYNTAX Integer32
		
		MAX-ACCESS read-only
		STATUS current
		DESCRIPTION
		"upsApm160snmp_1169_OnputSource1PhaseVoltageA stored as 0.01V."
		::= { upsApm160snmpEntry 1169 }
upsApm160snmp_1170_OnputSource1PhaseVoltageB OBJECT-TYPE
		SYNTAX Integer32
		
		MAX-ACCESS read-only
		STATUS current
		DESCRIPTION
		"upsApm160snmp_1170_OnputSource1PhaseVoltageB stored as 0.01V."
		::= { upsApm160snmpEntry 1170 }
upsApm160snmp_1171_OnputSource1PhaseVoltageC OBJECT-TYPE
		SYNTAX Integer32
		
		MAX-ACCESS read-only
		STATUS current
		DESCRIPTION
		"upsApm160snmp_1171_OnputSource1PhaseVoltageC stored as 0.01V."
		::= { upsApm160snmpEntry 1171 }
upsApm160snmp_1172_OnputSource1FrequencyA OBJECT-TYPE
		SYNTAX Integer32
		
		MAX-ACCESS read-only
		STATUS current
		DESCRIPTION
		"upsApm160snmp_1172_OnputSource1FrequencyA stored as 0.01Hz."
		::= { upsApm160snmpEntry 1172 }
upsApm160snmp_1173_OnputSource1FrequencyB OBJECT-TYPE
		SYNTAX Integer32
		
		MAX-ACCESS read-only
		STATUS current
		DESCRIPTION
		"upsApm160snmp_1173_OnputSource1FrequencyB stored as 0.01Hz."
		::= { upsApm160snmpEntry 1173 }
upsApm160snmp_1174_OnputSource1FrequencyC OBJECT-TYPE
		SYNTAX Integer32
		
		MAX-ACCESS read-only
		STATUS current
		DESCRIPTION
		"upsApm160snmp_1174_OnputSource1FrequencyC stored as 0.01Hz."
		::= { upsApm160snmpEntry 1174 }
upsApm160snmp_1175_OnputSource1THDuA OBJECT-TYPE
		SYNTAX Integer32
		
		MAX-ACCESS read-only
		STATUS current
		DESCRIPTION
		"upsApm160snmp_1175_OnputSource1THDuA stored as 0.01%."
		::= { upsApm160snmpEntry 1175 }
upsApm160snmp_1176_OnputSource1THDuB OBJECT-TYPE
		SYNTAX Integer32
		
		MAX-ACCESS read-only
		STATUS current
		DESCRIPTION
		"upsApm160snmp_1176_OnputSource1THDuB stored as 0.01%."
		::= { upsApm160snmpEntry 1176 }
upsApm160snmp_1177_OnputSource1THDuC OBJECT-TYPE
		SYNTAX Integer32
		
		MAX-ACCESS read-only
		STATUS current
		DESCRIPTION
		"upsApm160snmp_1177_OnputSource1THDuC stored as 0.01%."
		::= { upsApm160snmpEntry 1177 }
upsApm160snmp_1178_UPSCommunicationInterrupt OBJECT-TYPE
		SYNTAX INTEGER {
			normal(0),
			alarm(1) }
		MAX-ACCESS read-only
		STATUS current
		DESCRIPTION
		"upsApm160snmp_1178_UPSCommunicationInterrupt status."
		::= { upsApm160snmpEntry 1178 }
upsApm160snmp_1179_UPSCommunicationInterruptRec OBJECT-TYPE
		SYNTAX INTEGER {
			normal(0),
			alarm(1) }
		MAX-ACCESS read-only
		STATUS current
		DESCRIPTION
		"upsApm160snmp_1179_UPSCommunicationInterruptRec status."
		::= { upsApm160snmpEntry 1179 }
upsApm160snmp_1180_UPSNoOutput OBJECT-TYPE
		SYNTAX INTEGER {
			normal(0),
			alarm(1) }
		MAX-ACCESS read-only
		STATUS current
		DESCRIPTION
		"upsApm160snmp_1180_UPSNoOutput status."
		::= { upsApm160snmpEntry 1180 }
upsApm160snmp_1181_UPSOnBypass OBJECT-TYPE
		SYNTAX INTEGER {
			normal(0),
			alarm(1) }
		MAX-ACCESS read-only
		STATUS current
		DESCRIPTION
		"upsApm160snmp_1181_UPSOnBypass status."
		::= { upsApm160snmpEntry 1181 }
upsApm160snmp_1182_UPSinNormalMode OBJECT-TYPE
		SYNTAX INTEGER {
			normal(0),
			alarm(1) }
		MAX-ACCESS read-only
		STATUS current
		DESCRIPTION
		"upsApm160snmp_1182_UPSinNormalMode status."
		::= { upsApm160snmpEntry 1182 }
upsApm160snmp_1183_UPSinBatteryMode OBJECT-TYPE
		SYNTAX INTEGER {
			normal(0),
			alarm(1) }
		MAX-ACCESS read-only
		STATUS current
		DESCRIPTION
		"upsApm160snmp_1183_UPSinBatteryMode status."
		::= { upsApm160snmpEntry 1183 }
upsApm160snmp_1184_BatteryTestInitiated OBJECT-TYPE
		SYNTAX INTEGER {
			normal(0),
			alarm(1) }
		MAX-ACCESS read-only
		STATUS current
		DESCRIPTION
		"upsApm160snmp_1184_BatteryTestInitiated status."
		::= { upsApm160snmpEntry 1184 }
upsApm160snmp_1185_BatteryNotInTesting OBJECT-TYPE
		SYNTAX INTEGER {
			normal(0),
			alarm(1) }
		MAX-ACCESS read-only
		STATUS current
		DESCRIPTION
		"upsApm160snmp_1185_BatteryNotInTesting status."
		::= { upsApm160snmpEntry 1185 }
upsApm160snmp_1186_BatteryFloatCharging OBJECT-TYPE
		SYNTAX INTEGER {
			normal(0),
			alarm(1) }
		MAX-ACCESS read-only
		STATUS current
		DESCRIPTION
		"upsApm160snmp_1186_BatteryFloatCharging status."
		::= { upsApm160snmpEntry 1186 }
upsApm160snmp_1187_BatteryBoostCharging OBJECT-TYPE
		SYNTAX INTEGER {
			normal(0),
			alarm(1) }
		MAX-ACCESS read-only
		STATUS current
		DESCRIPTION
		"upsApm160snmp_1187_BatteryBoostCharging status."
		::= { upsApm160snmpEntry 1187 }
upsApm160snmp_1188_BatteryNotInCharging OBJECT-TYPE
		SYNTAX INTEGER {
			normal(0),
			alarm(1) }
		MAX-ACCESS read-only
		STATUS current
		DESCRIPTION
		"upsApm160snmp_1188_BatteryNotInCharging status."
		::= { upsApm160snmpEntry 1188 }
upsApm160snmp_1189_UPSInverterOff OBJECT-TYPE
		SYNTAX INTEGER {
			normal(0),
			alarm(1) }
		MAX-ACCESS read-only
		STATUS current
		DESCRIPTION
		"upsApm160snmp_1189_UPSInverterOff status."
		::= { upsApm160snmpEntry 1189 }
upsApm160snmp_1190_UPSInverterOn OBJECT-TYPE
		SYNTAX INTEGER {
			normal(0),
			alarm(1) }
		MAX-ACCESS read-only
		STATUS current
		DESCRIPTION
		"upsApm160snmp_1190_UPSInverterOn status."
		::= { upsApm160snmpEntry 1190 }
upsApm160snmp_1191_OnGenerator OBJECT-TYPE
		SYNTAX INTEGER {
			normal(0),
			alarm(1) }
		MAX-ACCESS read-only
		STATUS current
		DESCRIPTION
		"upsApm160snmp_1191_OnGenerator status."
		::= { upsApm160snmpEntry 1191 }
upsApm160snmp_1192_NotOnGenerator OBJECT-TYPE
		SYNTAX INTEGER {
			normal(0),
			alarm(1) }
		MAX-ACCESS read-only
		STATUS current
		DESCRIPTION
		"upsApm160snmp_1192_NotOnGenerator status."
		::= { upsApm160snmpEntry 1192 }
upsApm160snmp_1193_InputSwitchOpen OBJECT-TYPE
		SYNTAX INTEGER {
			normal(0),
			alarm(1) }
		MAX-ACCESS read-only
		STATUS current
		DESCRIPTION
		"upsApm160snmp_1193_InputSwitchOpen status."
		::= { upsApm160snmpEntry 1193 }
upsApm160snmp_1194_InputSwitchClosed OBJECT-TYPE
		SYNTAX INTEGER {
			normal(0),
			alarm(1) }
		MAX-ACCESS read-only
		STATUS current
		DESCRIPTION
		"upsApm160snmp_1194_InputSwitchClosed status."
		::= { upsApm160snmpEntry 1194 }
upsApm160snmp_1195_MaintainenceSwitchOpen OBJECT-TYPE
		SYNTAX INTEGER {
			normal(0),
			alarm(1) }
		MAX-ACCESS read-only
		STATUS current
		DESCRIPTION
		"upsApm160snmp_1195_MaintainenceSwitchOpen status."
		::= { upsApm160snmpEntry 1195 }
upsApm160snmp_1196_MaintainenceSwitchClosed OBJECT-TYPE
		SYNTAX INTEGER {
			normal(0),
			alarm(1) }
		MAX-ACCESS read-only
		STATUS current
		DESCRIPTION
		"upsApm160snmp_1196_MaintainenceSwitchClosed status."
		::= { upsApm160snmpEntry 1196 }
upsApm160snmp_1197_BypassSwitchOpen OBJECT-TYPE
		SYNTAX INTEGER {
			normal(0),
			alarm(1) }
		MAX-ACCESS read-only
		STATUS current
		DESCRIPTION
		"upsApm160snmp_1197_BypassSwitchOpen status."
		::= { upsApm160snmpEntry 1197 }
upsApm160snmp_1198_BypassSwitchClosed OBJECT-TYPE
		SYNTAX INTEGER {
			normal(0),
			alarm(1) }
		MAX-ACCESS read-only
		STATUS current
		DESCRIPTION
		"upsApm160snmp_1198_BypassSwitchClosed status."
		::= { upsApm160snmpEntry 1198 }
upsApm160snmp_1199_OutputSwitchOpen OBJECT-TYPE
		SYNTAX INTEGER {
			normal(0),
			alarm(1) }
		MAX-ACCESS read-only
		STATUS current
		DESCRIPTION
		"upsApm160snmp_1199_OutputSwitchOpen status."
		::= { upsApm160snmpEntry 1199 }
upsApm160snmp_1200_OutputSwitchClosed OBJECT-TYPE
		SYNTAX INTEGER {
			normal(0),
			alarm(1) }
		MAX-ACCESS read-only
		STATUS current
		DESCRIPTION
		"upsApm160snmp_1200_OutputSwitchClosed status."
		::= { upsApm160snmpEntry 1200 }
upsApm160snmp_1201_ExternalMaintanceswitchOpen OBJECT-TYPE
		SYNTAX INTEGER {
			normal(0),
			alarm(1) }
		MAX-ACCESS read-only
		STATUS current
		DESCRIPTION
		"upsApm160snmp_1201_ExternalMaintanceswitchOpen status."
		::= { upsApm160snmpEntry 1201 }
upsApm160snmp_1202_ExternalMaintanceswitchClose OBJECT-TYPE
		SYNTAX INTEGER {
			normal(0),
			alarm(1) }
		MAX-ACCESS read-only
		STATUS current
		DESCRIPTION
		"upsApm160snmp_1202_ExternalMaintanceswitchClose status."
		::= { upsApm160snmpEntry 1202 }
upsApm160snmp_1203_ExternalOutputswitchOpen OBJECT-TYPE
		SYNTAX INTEGER {
			normal(0),
			alarm(1) }
		MAX-ACCESS read-only
		STATUS current
		DESCRIPTION
		"upsApm160snmp_1203_ExternalOutputswitchOpen status."
		::= { upsApm160snmpEntry 1203 }
upsApm160snmp_1204_ExternalOutputswitchClosed OBJECT-TYPE
		SYNTAX INTEGER {
			normal(0),
			alarm(1) }
		MAX-ACCESS read-only
		STATUS current
		DESCRIPTION
		"upsApm160snmp_1204_ExternalOutputswitchClosed status."
		::= { upsApm160snmpEntry 1204 }
upsApm160snmp_1205_ExternalMaintIsolationswitc OBJECT-TYPE
		SYNTAX INTEGER {
			normal(0),
			alarm(1) }
		MAX-ACCESS read-only
		STATUS current
		DESCRIPTION
		"upsApm160snmp_1205_ExternalMaintIsolationswitc status."
		::= { upsApm160snmpEntry 1205 }
upsApm160snmp_1206_ExternalMaintIsolationswitc OBJECT-TYPE
		SYNTAX INTEGER {
			normal(0),
			alarm(1) }
		MAX-ACCESS read-only
		STATUS current
		DESCRIPTION
		"upsApm160snmp_1206_ExternalMaintIsolationswitc status."
		::= { upsApm160snmpEntry 1206 }
upsApm160snmp_1207_BCBAbsent OBJECT-TYPE
		SYNTAX INTEGER {
			normal(0),
			alarm(1) }
		MAX-ACCESS read-only
		STATUS current
		DESCRIPTION
		"upsApm160snmp_1207_BCBAbsent status."
		::= { upsApm160snmpEntry 1207 }
upsApm160snmp_1208_BCBClosed OBJECT-TYPE
		SYNTAX INTEGER {
			normal(0),
			alarm(1) }
		MAX-ACCESS read-only
		STATUS current
		DESCRIPTION
		"upsApm160snmp_1208_BCBClosed status."
		::= { upsApm160snmpEntry 1208 }
upsApm160snmp_1209_BCBOpen OBJECT-TYPE
		SYNTAX INTEGER {
			normal(0),
			alarm(1) }
		MAX-ACCESS read-only
		STATUS current
		DESCRIPTION
		"upsApm160snmp_1209_BCBOpen status."
		::= { upsApm160snmpEntry 1209 }
upsApm160snmp_1210_ModuleRunning OBJECT-TYPE
		SYNTAX INTEGER {
			normal(0),
			alarm(1) }
		MAX-ACCESS read-only
		STATUS current
		DESCRIPTION
		"upsApm160snmp_1210_ModuleRunning status."
		::= { upsApm160snmpEntry 1210 }
upsApm160snmp_1211_ModuleSleeping OBJECT-TYPE
		SYNTAX INTEGER {
			normal(0),
			alarm(1) }
		MAX-ACCESS read-only
		STATUS current
		DESCRIPTION
		"upsApm160snmp_1211_ModuleSleeping status."
		::= { upsApm160snmpEntry 1211 }
upsApm160snmp_1212_InverterAsynchronousRecovered OBJECT-TYPE
		SYNTAX INTEGER {
			normal(0),
			alarm(1) }
		MAX-ACCESS read-only
		STATUS current
		DESCRIPTION
		"upsApm160snmp_1212_InverterAsynchronousRecovered status."
		::= { upsApm160snmpEntry 1212 }
upsApm160snmp_1213_InverterAsynchronous OBJECT-TYPE
		SYNTAX INTEGER {
			normal(0),
			alarm(1) }
		MAX-ACCESS read-only
		STATUS current
		DESCRIPTION
		"upsApm160snmp_1213_InverterAsynchronous status."
		::= { upsApm160snmpEntry 1213 }
upsApm160snmp_1214_InputVoltageAbnormalRecovere OBJECT-TYPE
		SYNTAX INTEGER {
			normal(0),
			alarm(1) }
		MAX-ACCESS read-only
		STATUS current
		DESCRIPTION
		"upsApm160snmp_1214_InputVoltageAbnormalRecovere status."
		::= { upsApm160snmpEntry 1214 }
upsApm160snmp_1215_InputVoltageAbnormal OBJECT-TYPE
		SYNTAX INTEGER {
			normal(0),
			alarm(1) }
		MAX-ACCESS read-only
		STATUS current
		DESCRIPTION
		"upsApm160snmp_1215_InputVoltageAbnormal status."
		::= { upsApm160snmpEntry 1215 }
upsApm160snmp_1216_RectifierFaultRecovered OBJECT-TYPE
		SYNTAX INTEGER {
			normal(0),
			alarm(1) }
		MAX-ACCESS read-only
		STATUS current
		DESCRIPTION
		"upsApm160snmp_1216_RectifierFaultRecovered status."
		::= { upsApm160snmpEntry 1216 }
upsApm160snmp_1217_RectifierFault OBJECT-TYPE
		SYNTAX INTEGER {
			normal(0),
			alarm(1) }
		MAX-ACCESS read-only
		STATUS current
		DESCRIPTION
		"upsApm160snmp_1217_RectifierFault status."
		::= { upsApm160snmpEntry 1217 }
upsApm160snmp_1218_InverterFaultRecovered OBJECT-TYPE
		SYNTAX INTEGER {
			normal(0),
			alarm(1) }
		MAX-ACCESS read-only
		STATUS current
		DESCRIPTION
		"upsApm160snmp_1218_InverterFaultRecovered status."
		::= { upsApm160snmpEntry 1218 }
upsApm160snmp_1219_InverterFault OBJECT-TYPE
		SYNTAX INTEGER {
			normal(0),
			alarm(1) }
		MAX-ACCESS read-only
		STATUS current
		DESCRIPTION
		"upsApm160snmp_1219_InverterFault status."
		::= { upsApm160snmpEntry 1219 }
upsApm160snmp_1220_BypassAbnormalRecovered OBJECT-TYPE
		SYNTAX INTEGER {
			normal(0),
			alarm(1) }
		MAX-ACCESS read-only
		STATUS current
		DESCRIPTION
		"upsApm160snmp_1220_BypassAbnormalRecovered status."
		::= { upsApm160snmpEntry 1220 }
upsApm160snmp_1221_BypassAbnormal OBJECT-TYPE
		SYNTAX INTEGER {
			normal(0),
			alarm(1) }
		MAX-ACCESS read-only
		STATUS current
		DESCRIPTION
		"upsApm160snmp_1221_BypassAbnormal status."
		::= { upsApm160snmpEntry 1221 }
upsApm160snmp_1222_BatteryNormal OBJECT-TYPE
		SYNTAX INTEGER {
			normal(0),
			alarm(1) }
		MAX-ACCESS read-only
		STATUS current
		DESCRIPTION
		"upsApm160snmp_1222_BatteryNormal status."
		::= { upsApm160snmpEntry 1222 }
upsApm160snmp_1223_BatteryUndervoltage OBJECT-TYPE
		SYNTAX INTEGER {
			normal(0),
			alarm(1) }
		MAX-ACCESS read-only
		STATUS current
		DESCRIPTION
		"upsApm160snmp_1223_BatteryUndervoltage status."
		::= { upsApm160snmpEntry 1223 }
upsApm160snmp_1224_BatteryOvervoltage OBJECT-TYPE
		SYNTAX INTEGER {
			normal(0),
			alarm(1) }
		MAX-ACCESS read-only
		STATUS current
		DESCRIPTION
		"upsApm160snmp_1224_BatteryOvervoltage status."
		::= { upsApm160snmpEntry 1224 }
upsApm160snmp_1225_NoBattery OBJECT-TYPE
		SYNTAX INTEGER {
			normal(0),
			alarm(1) }
		MAX-ACCESS read-only
		STATUS current
		DESCRIPTION
		"upsApm160snmp_1225_NoBattery status."
		::= { upsApm160snmpEntry 1225 }
upsApm160snmp_1226_LowBatteryWarning OBJECT-TYPE
		SYNTAX INTEGER {
			normal(0),
			alarm(1) }
		MAX-ACCESS read-only
		STATUS current
		DESCRIPTION
		"upsApm160snmp_1226_LowBatteryWarning status."
		::= { upsApm160snmpEntry 1226 }
upsApm160snmp_1227_BatteryReversed OBJECT-TYPE
		SYNTAX INTEGER {
			normal(0),
			alarm(1) }
		MAX-ACCESS read-only
		STATUS current
		DESCRIPTION
		"upsApm160snmp_1227_BatteryReversed status."
		::= { upsApm160snmpEntry 1227 }
upsApm160snmp_1228_AmbientOvertemperatureRecover OBJECT-TYPE
		SYNTAX INTEGER {
			normal(0),
			alarm(1) }
		MAX-ACCESS read-only
		STATUS current
		DESCRIPTION
		"upsApm160snmp_1228_AmbientOvertemperatureRecover status."
		::= { upsApm160snmpEntry 1228 }
upsApm160snmp_1229_AmbientOvertemperatureRecover OBJECT-TYPE
		SYNTAX INTEGER {
			normal(0),
			alarm(1) }
		MAX-ACCESS read-only
		STATUS current
		DESCRIPTION
		"upsApm160snmp_1229_AmbientOvertemperatureRecover status."
		::= { upsApm160snmpEntry 1229 }
upsApm160snmp_1230_PowerCANCommunicationnormal OBJECT-TYPE
		SYNTAX INTEGER {
			normal(0),
			alarm(1) }
		MAX-ACCESS read-only
		STATUS current
		DESCRIPTION
		"upsApm160snmp_1230_PowerCANCommunicationnormal status."
		::= { upsApm160snmpEntry 1230 }
upsApm160snmp_1231_PowerCANCommunicationAbnormal OBJECT-TYPE
		SYNTAX INTEGER {
			normal(0),
			alarm(1) }
		MAX-ACCESS read-only
		STATUS current
		DESCRIPTION
		"upsApm160snmp_1231_PowerCANCommunicationAbnormal status."
		::= { upsApm160snmpEntry 1231 }
upsApm160snmp_1232_RecDSPSWErrorRecovered OBJECT-TYPE
		SYNTAX INTEGER {
			normal(0),
			alarm(1) }
		MAX-ACCESS read-only
		STATUS current
		DESCRIPTION
		"upsApm160snmp_1232_RecDSPSWErrorRecovered status."
		::= { upsApm160snmpEntry 1232 }
upsApm160snmp_1233_RecDSPSWError OBJECT-TYPE
		SYNTAX INTEGER {
			normal(0),
			alarm(1) }
		MAX-ACCESS read-only
		STATUS current
		DESCRIPTION
		"upsApm160snmp_1233_RecDSPSWError status."
		::= { upsApm160snmpEntry 1233 }
upsApm160snmp_1234_OutputDisabledRecovered OBJECT-TYPE
		SYNTAX INTEGER {
			normal(0),
			alarm(1) }
		MAX-ACCESS read-only
		STATUS current
		DESCRIPTION
		"upsApm160snmp_1234_OutputDisabledRecovered status."
		::= { upsApm160snmpEntry 1234 }
upsApm160snmp_1235_OutputDisabled OBJECT-TYPE
		SYNTAX INTEGER {
			normal(0),
			alarm(1) }
		MAX-ACCESS read-only
		STATUS current
		DESCRIPTION
		"upsApm160snmp_1235_OutputDisabled status."
		::= { upsApm160snmpEntry 1235 }
upsApm160snmp_1236_InverterDSPSoftwareErrorRec OBJECT-TYPE
		SYNTAX INTEGER {
			normal(0),
			alarm(1) }
		MAX-ACCESS read-only
		STATUS current
		DESCRIPTION
		"upsApm160snmp_1236_InverterDSPSoftwareErrorRec status."
		::= { upsApm160snmpEntry 1236 }
upsApm160snmp_1237_InverterDSPSoftwareError OBJECT-TYPE
		SYNTAX INTEGER {
			normal(0),
			alarm(1) }
		MAX-ACCESS read-only
		STATUS current
		DESCRIPTION
		"upsApm160snmp_1237_InverterDSPSoftwareError status."
		::= { upsApm160snmpEntry 1237 }
upsApm160snmp_1238_InverterFPGASoftwareErrorRe OBJECT-TYPE
		SYNTAX INTEGER {
			normal(0),
			alarm(1) }
		MAX-ACCESS read-only
		STATUS current
		DESCRIPTION
		"upsApm160snmp_1238_InverterFPGASoftwareErrorRe status."
		::= { upsApm160snmpEntry 1238 }
upsApm160snmp_1239_InverterFPGASoftwareError OBJECT-TYPE
		SYNTAX INTEGER {
			normal(0),
			alarm(1) }
		MAX-ACCESS read-only
		STATUS current
		DESCRIPTION
		"upsApm160snmp_1239_InverterFPGASoftwareError status."
		::= { upsApm160snmpEntry 1239 }
upsApm160snmp_1240_BypassDSPSoftwareErrorRecov OBJECT-TYPE
		SYNTAX INTEGER {
			normal(0),
			alarm(1) }
		MAX-ACCESS read-only
		STATUS current
		DESCRIPTION
		"upsApm160snmp_1240_BypassDSPSoftwareErrorRecov status."
		::= { upsApm160snmpEntry 1240 }
upsApm160snmp_1241_BypassDSPSoftwareError OBJECT-TYPE
		SYNTAX INTEGER {
			normal(0),
			alarm(1) }
		MAX-ACCESS read-only
		STATUS current
		DESCRIPTION
		"upsApm160snmp_1241_BypassDSPSoftwareError status."
		::= { upsApm160snmpEntry 1241 }
upsApm160snmp_1242_BypassFPGASoftwareErrorReco OBJECT-TYPE
		SYNTAX INTEGER {
			normal(0),
			alarm(1) }
		MAX-ACCESS read-only
		STATUS current
		DESCRIPTION
		"upsApm160snmp_1242_BypassFPGASoftwareErrorReco status."
		::= { upsApm160snmpEntry 1242 }
upsApm160snmp_1243_BypassFPGASoftwareError OBJECT-TYPE
		SYNTAX INTEGER {
			normal(0),
			alarm(1) }
		MAX-ACCESS read-only
		STATUS current
		DESCRIPTION
		"upsApm160snmp_1243_BypassFPGASoftwareError status."
		::= { upsApm160snmpEntry 1243 }
upsApm160snmp_1244_DiscreteBusCommunicationNorm OBJECT-TYPE
		SYNTAX INTEGER {
			normal(0),
			alarm(1) }
		MAX-ACCESS read-only
		STATUS current
		DESCRIPTION
		"upsApm160snmp_1244_DiscreteBusCommunicationNorm status."
		::= { upsApm160snmpEntry 1244 }
upsApm160snmp_1245_DiscreteBusCommunicationAbno OBJECT-TYPE
		SYNTAX INTEGER {
			normal(0),
			alarm(1) }
		MAX-ACCESS read-only
		STATUS current
		DESCRIPTION
		"upsApm160snmp_1245_DiscreteBusCommunicationAbno status."
		::= { upsApm160snmpEntry 1245 }
upsApm160snmp_1246_LBSAbnormalRecovered OBJECT-TYPE
		SYNTAX INTEGER {
			normal(0),
			alarm(1) }
		MAX-ACCESS read-only
		STATUS current
		DESCRIPTION
		"upsApm160snmp_1246_LBSAbnormalRecovered status."
		::= { upsApm160snmpEntry 1246 }
upsApm160snmp_1247_LBSAbnormal OBJECT-TYPE
		SYNTAX INTEGER {
			normal(0),
			alarm(1) }
		MAX-ACCESS read-only
		STATUS current
		DESCRIPTION
		"upsApm160snmp_1247_LBSAbnormal status."
		::= { upsApm160snmpEntry 1247 }
upsApm160snmp_1248_EPORecovered OBJECT-TYPE
		SYNTAX INTEGER {
			normal(0),
			alarm(1) }
		MAX-ACCESS read-only
		STATUS current
		DESCRIPTION
		"upsApm160snmp_1248_EPORecovered status."
		::= { upsApm160snmpEntry 1248 }
upsApm160snmp_1249_EPO OBJECT-TYPE
		SYNTAX INTEGER {
			normal(0),
			alarm(1) }
		MAX-ACCESS read-only
		STATUS current
		DESCRIPTION
		"upsApm160snmp_1249_EPO status."
		::= { upsApm160snmpEntry 1249 }
upsApm160snmp_1250_BypassSTSFailRecovered OBJECT-TYPE
		SYNTAX INTEGER {
			normal(0),
			alarm(1) }
		MAX-ACCESS read-only
		STATUS current
		DESCRIPTION
		"upsApm160snmp_1250_BypassSTSFailRecovered status."
		::= { upsApm160snmpEntry 1250 }
upsApm160snmp_1251_BypassSTSFail OBJECT-TYPE
		SYNTAX INTEGER {
			normal(0),
			alarm(1) }
		MAX-ACCESS read-only
		STATUS current
		DESCRIPTION
		"upsApm160snmp_1251_BypassSTSFail status."
		::= { upsApm160snmpEntry 1251 }
upsApm160snmp_1252_BypassPhaseReversedRecovered OBJECT-TYPE
		SYNTAX INTEGER {
			normal(0),
			alarm(1) }
		MAX-ACCESS read-only
		STATUS current
		DESCRIPTION
		"upsApm160snmp_1252_BypassPhaseReversedRecovered status."
		::= { upsApm160snmpEntry 1252 }
upsApm160snmp_1253_BypassPhaseReversed OBJECT-TYPE
		SYNTAX INTEGER {
			normal(0),
			alarm(1) }
		MAX-ACCESS read-only
		STATUS current
		DESCRIPTION
		"upsApm160snmp_1253_BypassPhaseReversed status."
		::= { upsApm160snmpEntry 1253 }
upsApm160snmp_1254_BypassOvercurrentRecovered OBJECT-TYPE
		SYNTAX INTEGER {
			normal(0),
			alarm(1) }
		MAX-ACCESS read-only
		STATUS current
		DESCRIPTION
		"upsApm160snmp_1254_BypassOvercurrentRecovered status."
		::= { upsApm160snmpEntry 1254 }
upsApm160snmp_1255_BypassOvercurrent OBJECT-TYPE
		SYNTAX INTEGER {
			normal(0),
			alarm(1) }
		MAX-ACCESS read-only
		STATUS current
		DESCRIPTION
		"upsApm160snmp_1255_BypassOvercurrent status."
		::= { upsApm160snmpEntry 1255 }
upsApm160snmp_1256_BypassAbnormalShutdownRecove OBJECT-TYPE
		SYNTAX INTEGER {
			normal(0),
			alarm(1) }
		MAX-ACCESS read-only
		STATUS current
		DESCRIPTION
		"upsApm160snmp_1256_BypassAbnormalShutdownRecove status."
		::= { upsApm160snmpEntry 1256 }
upsApm160snmp_1257_BypassAbnormalShutdown OBJECT-TYPE
		SYNTAX INTEGER {
			normal(0),
			alarm(1) }
		MAX-ACCESS read-only
		STATUS current
		DESCRIPTION
		"upsApm160snmp_1257_BypassAbnormalShutdown status."
		::= { upsApm160snmpEntry 1257 }
upsApm160snmp_1258_ExcessAutoRexfersRecovered OBJECT-TYPE
		SYNTAX INTEGER {
			normal(0),
			alarm(1) }
		MAX-ACCESS read-only
		STATUS current
		DESCRIPTION
		"upsApm160snmp_1258_ExcessAutoRexfersRecovered status."
		::= { upsApm160snmpEntry 1258 }
upsApm160snmp_1259_ExcessAutoRexfers OBJECT-TYPE
		SYNTAX INTEGER {
			normal(0),
			alarm(1) }
		MAX-ACCESS read-only
		STATUS current
		DESCRIPTION
		"upsApm160snmp_1259_ExcessAutoRexfers status."
		::= { upsApm160snmpEntry 1259 }
upsApm160snmp_1260_ExcessECOAutoXfersRecovered OBJECT-TYPE
		SYNTAX INTEGER {
			normal(0),
			alarm(1) }
		MAX-ACCESS read-only
		STATUS current
		DESCRIPTION
		"upsApm160snmp_1260_ExcessECOAutoXfersRecovered status."
		::= { upsApm160snmpEntry 1260 }
upsApm160snmp_1261_ExcessECOAutoXfers OBJECT-TYPE
		SYNTAX INTEGER {
			normal(0),
			alarm(1) }
		MAX-ACCESS read-only
		STATUS current
		DESCRIPTION
		"upsApm160snmp_1261_ExcessECOAutoXfers status."
		::= { upsApm160snmpEntry 1261 }
upsApm160snmp_1262_ParaPowerCANCommunicationAbno OBJECT-TYPE
		SYNTAX INTEGER {
			normal(0),
			alarm(1) }
		MAX-ACCESS read-only
		STATUS current
		DESCRIPTION
		"upsApm160snmp_1262_ParaPowerCANCommunicationAbno status."
		::= { upsApm160snmpEntry 1262 }
upsApm160snmp_1263_ParaPowerCANCommunicationAbno OBJECT-TYPE
		SYNTAX INTEGER {
			normal(0),
			alarm(1) }
		MAX-ACCESS read-only
		STATUS current
		DESCRIPTION
		"upsApm160snmp_1263_ParaPowerCANCommunicationAbno status."
		::= { upsApm160snmpEntry 1263 }
upsApm160snmp_1264_DischargerCurrentLimitRecove OBJECT-TYPE
		SYNTAX INTEGER {
			normal(0),
			alarm(1) }
		MAX-ACCESS read-only
		STATUS current
		DESCRIPTION
		"upsApm160snmp_1264_DischargerCurrentLimitRecove status."
		::= { upsApm160snmpEntry 1264 }
upsApm160snmp_1265_DischargerCurrentLimit OBJECT-TYPE
		SYNTAX INTEGER {
			normal(0),
			alarm(1) }
		MAX-ACCESS read-only
		STATUS current
		DESCRIPTION
		"upsApm160snmp_1265_DischargerCurrentLimit status."
		::= { upsApm160snmpEntry 1265 }
upsApm160snmp_1266_DischargerFaultRecovered OBJECT-TYPE
		SYNTAX INTEGER {
			normal(0),
			alarm(1) }
		MAX-ACCESS read-only
		STATUS current
		DESCRIPTION
		"upsApm160snmp_1266_DischargerFaultRecovered status."
		::= { upsApm160snmpEntry 1266 }
upsApm160snmp_1267_DischargerFault OBJECT-TYPE
		SYNTAX INTEGER {
			normal(0),
			alarm(1) }
		MAX-ACCESS read-only
		STATUS current
		DESCRIPTION
		"upsApm160snmp_1267_DischargerFault status."
		::= { upsApm160snmpEntry 1267 }
upsApm160snmp_1268_ChargerFaultRecovered OBJECT-TYPE
		SYNTAX INTEGER {
			normal(0),
			alarm(1) }
		MAX-ACCESS read-only
		STATUS current
		DESCRIPTION
		"upsApm160snmp_1268_ChargerFaultRecovered status."
		::= { upsApm160snmpEntry 1268 }
upsApm160snmp_1269_ChargerFault OBJECT-TYPE
		SYNTAX INTEGER {
			normal(0),
			alarm(1) }
		MAX-ACCESS read-only
		STATUS current
		DESCRIPTION
		"upsApm160snmp_1269_ChargerFault status."
		::= { upsApm160snmpEntry 1269 }
upsApm160snmp_1270_LBSCableAbnormalRecovered OBJECT-TYPE
		SYNTAX INTEGER {
			normal(0),
			alarm(1) }
		MAX-ACCESS read-only
		STATUS current
		DESCRIPTION
		"upsApm160snmp_1270_LBSCableAbnormalRecovered status."
		::= { upsApm160snmpEntry 1270 }
upsApm160snmp_1271_LBSCableAbnormal OBJECT-TYPE
		SYNTAX INTEGER {
			normal(0),
			alarm(1) }
		MAX-ACCESS read-only
		STATUS current
		DESCRIPTION
		"upsApm160snmp_1271_LBSCableAbnormal status."
		::= { upsApm160snmpEntry 1271 }
upsApm160snmp_1272_BatteryMaintainRecovered OBJECT-TYPE
		SYNTAX INTEGER {
			normal(0),
			alarm(1) }
		MAX-ACCESS read-only
		STATUS current
		DESCRIPTION
		"upsApm160snmp_1272_BatteryMaintainRecovered status."
		::= { upsApm160snmpEntry 1272 }
upsApm160snmp_1273_BatteryMaintain OBJECT-TYPE
		SYNTAX INTEGER {
			normal(0),
			alarm(1) }
		MAX-ACCESS read-only
		STATUS current
		DESCRIPTION
		"upsApm160snmp_1273_BatteryMaintain status."
		::= { upsApm160snmpEntry 1273 }
upsApm160snmp_1274_BatteryOvertemperatureRecover OBJECT-TYPE
		SYNTAX INTEGER {
			normal(0),
			alarm(1) }
		MAX-ACCESS read-only
		STATUS current
		DESCRIPTION
		"upsApm160snmp_1274_BatteryOvertemperatureRecover status."
		::= { upsApm160snmpEntry 1274 }
upsApm160snmp_1275_BatteryOvertemperature OBJECT-TYPE
		SYNTAX INTEGER {
			normal(0),
			alarm(1) }
		MAX-ACCESS read-only
		STATUS current
		DESCRIPTION
		"upsApm160snmp_1275_BatteryOvertemperature status."
		::= { upsApm160snmpEntry 1275 }
upsApm160snmp_1276_BatteryGroundFaultRecovered OBJECT-TYPE
		SYNTAX INTEGER {
			normal(0),
			alarm(1) }
		MAX-ACCESS read-only
		STATUS current
		DESCRIPTION
		"upsApm160snmp_1276_BatteryGroundFaultRecovered status."
		::= { upsApm160snmpEntry 1276 }
upsApm160snmp_1277_BatteryGroundFault OBJECT-TYPE
		SYNTAX INTEGER {
			normal(0),
			alarm(1) }
		MAX-ACCESS read-only
		STATUS current
		DESCRIPTION
		"upsApm160snmp_1277_BatteryGroundFault status."
		::= { upsApm160snmpEntry 1277 }
upsApm160snmp_1278_InputFrequencyAbnormalRecove OBJECT-TYPE
		SYNTAX INTEGER {
			normal(0),
			alarm(1) }
		MAX-ACCESS read-only
		STATUS current
		DESCRIPTION
		"upsApm160snmp_1278_InputFrequencyAbnormalRecove status."
		::= { upsApm160snmpEntry 1278 }
upsApm160snmp_1279_InputFrequencyAbnormal OBJECT-TYPE
		SYNTAX INTEGER {
			normal(0),
			alarm(1) }
		MAX-ACCESS read-only
		STATUS current
		DESCRIPTION
		"upsApm160snmp_1279_InputFrequencyAbnormal status."
		::= { upsApm160snmpEntry 1279 }
upsApm160snmp_1280_ModuleOvertemperatureRecovere OBJECT-TYPE
		SYNTAX INTEGER {
			normal(0),
			alarm(1) }
		MAX-ACCESS read-only
		STATUS current
		DESCRIPTION
		"upsApm160snmp_1280_ModuleOvertemperatureRecovere status."
		::= { upsApm160snmpEntry 1280 }
upsApm160snmp_1281_ModuleOvertemperature OBJECT-TYPE
		SYNTAX INTEGER {
			normal(0),
			alarm(1) }
		MAX-ACCESS read-only
		STATUS current
		DESCRIPTION
		"upsApm160snmp_1281_ModuleOvertemperature status."
		::= { upsApm160snmpEntry 1281 }
upsApm160snmp_1282_InputTransformerOvertempReco OBJECT-TYPE
		SYNTAX INTEGER {
			normal(0),
			alarm(1) }
		MAX-ACCESS read-only
		STATUS current
		DESCRIPTION
		"upsApm160snmp_1282_InputTransformerOvertempReco status."
		::= { upsApm160snmpEntry 1282 }
upsApm160snmp_1283_InputTransformerOvertemperatu OBJECT-TYPE
		SYNTAX INTEGER {
			normal(0),
			alarm(1) }
		MAX-ACCESS read-only
		STATUS current
		DESCRIPTION
		"upsApm160snmp_1283_InputTransformerOvertemperatu status."
		::= { upsApm160snmpEntry 1283 }
upsApm160snmp_1284_BypassTransformerOvertempRec OBJECT-TYPE
		SYNTAX INTEGER {
			normal(0),
			alarm(1) }
		MAX-ACCESS read-only
		STATUS current
		DESCRIPTION
		"upsApm160snmp_1284_BypassTransformerOvertempRec status."
		::= { upsApm160snmpEntry 1284 }
upsApm160snmp_1285_BypassTransformerOvertemperat OBJECT-TYPE
		SYNTAX INTEGER {
			normal(0),
			alarm(1) }
		MAX-ACCESS read-only
		STATUS current
		DESCRIPTION
		"upsApm160snmp_1285_BypassTransformerOvertemperat status."
		::= { upsApm160snmpEntry 1285 }
upsApm160snmp_1286_EqualizeChargeTimeoutRecover OBJECT-TYPE
		SYNTAX INTEGER {
			normal(0),
			alarm(1) }
		MAX-ACCESS read-only
		STATUS current
		DESCRIPTION
		"upsApm160snmp_1286_EqualizeChargeTimeoutRecover status."
		::= { upsApm160snmpEntry 1286 }
upsApm160snmp_1287_EqualizeChargeTimeout OBJECT-TYPE
		SYNTAX INTEGER {
			normal(0),
			alarm(1) }
		MAX-ACCESS read-only
		STATUS current
		DESCRIPTION
		"upsApm160snmp_1287_EqualizeChargeTimeout status."
		::= { upsApm160snmpEntry 1287 }
upsApm160snmp_1288_ControlPowerFailRecovered OBJECT-TYPE
		SYNTAX INTEGER {
			normal(0),
			alarm(1) }
		MAX-ACCESS read-only
		STATUS current
		DESCRIPTION
		"upsApm160snmp_1288_ControlPowerFailRecovered status."
		::= { upsApm160snmpEntry 1288 }
upsApm160snmp_1289_ControlPowerFail OBJECT-TYPE
		SYNTAX INTEGER {
			normal(0),
			alarm(1) }
		MAX-ACCESS read-only
		STATUS current
		DESCRIPTION
		"upsApm160snmp_1289_ControlPowerFail status."
		::= { upsApm160snmpEntry 1289 }
upsApm160snmp_1290_InputPhaseReversedRecovered OBJECT-TYPE
		SYNTAX INTEGER {
			normal(0),
			alarm(1) }
		MAX-ACCESS read-only
		STATUS current
		DESCRIPTION
		"upsApm160snmp_1290_InputPhaseReversedRecovered status."
		::= { upsApm160snmpEntry 1290 }
upsApm160snmp_1291_InputPhaseReversed OBJECT-TYPE
		SYNTAX INTEGER {
			normal(0),
			alarm(1) }
		MAX-ACCESS read-only
		STATUS current
		DESCRIPTION
		"upsApm160snmp_1291_InputPhaseReversed status."
		::= { upsApm160snmpEntry 1291 }
upsApm160snmp_1292_RectifierSoftStartFailRecov OBJECT-TYPE
		SYNTAX INTEGER {
			normal(0),
			alarm(1) }
		MAX-ACCESS read-only
		STATUS current
		DESCRIPTION
		"upsApm160snmp_1292_RectifierSoftStartFailRecov status."
		::= { upsApm160snmpEntry 1292 }
upsApm160snmp_1293_RectifierSoftStartFail OBJECT-TYPE
		SYNTAX INTEGER {
			normal(0),
			alarm(1) }
		MAX-ACCESS read-only
		STATUS current
		DESCRIPTION
		"upsApm160snmp_1293_RectifierSoftStartFail status."
		::= { upsApm160snmpEntry 1293 }
upsApm160snmp_1294_OperationInvalidRecovered OBJECT-TYPE
		SYNTAX INTEGER {
			normal(0),
			alarm(1) }
		MAX-ACCESS read-only
		STATUS current
		DESCRIPTION
		"upsApm160snmp_1294_OperationInvalidRecovered status."
		::= { upsApm160snmpEntry 1294 }
upsApm160snmp_1295_OperationInvalid OBJECT-TYPE
		SYNTAX INTEGER {
			normal(0),
			alarm(1) }
		MAX-ACCESS read-only
		STATUS current
		DESCRIPTION
		"upsApm160snmp_1295_OperationInvalid status."
		::= { upsApm160snmpEntry 1295 }
upsApm160snmp_1296_OutputOverloadRecovered OBJECT-TYPE
		SYNTAX INTEGER {
			normal(0),
			alarm(1) }
		MAX-ACCESS read-only
		STATUS current
		DESCRIPTION
		"upsApm160snmp_1296_OutputOverloadRecovered status."
		::= { upsApm160snmpEntry 1296 }
upsApm160snmp_1297_OutputOverload OBJECT-TYPE
		SYNTAX INTEGER {
			normal(0),
			alarm(1) }
		MAX-ACCESS read-only
		STATUS current
		DESCRIPTION
		"upsApm160snmp_1297_OutputOverload status."
		::= { upsApm160snmpEntry 1297 }
upsApm160snmp_1298_MMSCapacityExceededRecovered OBJECT-TYPE
		SYNTAX INTEGER {
			normal(0),
			alarm(1) }
		MAX-ACCESS read-only
		STATUS current
		DESCRIPTION
		"upsApm160snmp_1298_MMSCapacityExceededRecovered status."
		::= { upsApm160snmpEntry 1298 }
upsApm160snmp_1299_MMSCapacityExceeded OBJECT-TYPE
		SYNTAX INTEGER {
			normal(0),
			alarm(1) }
		MAX-ACCESS read-only
		STATUS current
		DESCRIPTION
		"upsApm160snmp_1299_MMSCapacityExceeded status."
		::= { upsApm160snmpEntry 1299 }
upsApm160snmp_1300_OutputOverloadTimeoutRecover OBJECT-TYPE
		SYNTAX INTEGER {
			normal(0),
			alarm(1) }
		MAX-ACCESS read-only
		STATUS current
		DESCRIPTION
		"upsApm160snmp_1300_OutputOverloadTimeoutRecover status."
		::= { upsApm160snmpEntry 1300 }
upsApm160snmp_1301_OutputOverloadTimeout OBJECT-TYPE
		SYNTAX INTEGER {
			normal(0),
			alarm(1) }
		MAX-ACCESS read-only
		STATUS current
		DESCRIPTION
		"upsApm160snmp_1301_OutputOverloadTimeout status."
		::= { upsApm160snmpEntry 1301 }
upsApm160snmp_1302_LoadImpactTransferRecovered OBJECT-TYPE
		SYNTAX INTEGER {
			normal(0),
			alarm(1) }
		MAX-ACCESS read-only
		STATUS current
		DESCRIPTION
		"upsApm160snmp_1302_LoadImpactTransferRecovered status."
		::= { upsApm160snmpEntry 1302 }
upsApm160snmp_1303_LoadImpactTransfer OBJECT-TYPE
		SYNTAX INTEGER {
			normal(0),
			alarm(1) }
		MAX-ACCESS read-only
		STATUS current
		DESCRIPTION
		"upsApm160snmp_1303_LoadImpactTransfer status."
		::= { upsApm160snmpEntry 1303 }
upsApm160snmp_1304_LoadSharingAbnormalRecovered OBJECT-TYPE
		SYNTAX INTEGER {
			normal(0),
			alarm(1) }
		MAX-ACCESS read-only
		STATUS current
		DESCRIPTION
		"upsApm160snmp_1304_LoadSharingAbnormalRecovered status."
		::= { upsApm160snmpEntry 1304 }
upsApm160snmp_1305_LoadSharingAbnormal OBJECT-TYPE
		SYNTAX INTEGER {
			normal(0),
			alarm(1) }
		MAX-ACCESS read-only
		STATUS current
		DESCRIPTION
		"upsApm160snmp_1305_LoadSharingAbnormal status."
		::= { upsApm160snmpEntry 1305 }
upsApm160snmp_1306_DCBusAbnormalShutdownRecove OBJECT-TYPE
		SYNTAX INTEGER {
			normal(0),
			alarm(1) }
		MAX-ACCESS read-only
		STATUS current
		DESCRIPTION
		"upsApm160snmp_1306_DCBusAbnormalShutdownRecove status."
		::= { upsApm160snmpEntry 1306 }
upsApm160snmp_1307_DCBusAbnormalShutdown OBJECT-TYPE
		SYNTAX INTEGER {
			normal(0),
			alarm(1) }
		MAX-ACCESS read-only
		STATUS current
		DESCRIPTION
		"upsApm160snmp_1307_DCBusAbnormalShutdown status."
		::= { upsApm160snmpEntry 1307 }
upsApm160snmp_1308_OtherModuleXferRecovered OBJECT-TYPE
		SYNTAX INTEGER {
			normal(0),
			alarm(1) }
		MAX-ACCESS read-only
		STATUS current
		DESCRIPTION
		"upsApm160snmp_1308_OtherModuleXferRecovered status."
		::= { upsApm160snmpEntry 1308 }
upsApm160snmp_1309_OtherModuleXfer OBJECT-TYPE
		SYNTAX INTEGER {
			normal(0),
			alarm(1) }
		MAX-ACCESS read-only
		STATUS current
		DESCRIPTION
		"upsApm160snmp_1309_OtherModuleXfer status."
		::= { upsApm160snmpEntry 1309 }
upsApm160snmp_1310_DCBusOvervoltageRecovered OBJECT-TYPE
		SYNTAX INTEGER {
			normal(0),
			alarm(1) }
		MAX-ACCESS read-only
		STATUS current
		DESCRIPTION
		"upsApm160snmp_1310_DCBusOvervoltageRecovered status."
		::= { upsApm160snmpEntry 1310 }
upsApm160snmp_1311_DCBusOvervoltage OBJECT-TYPE
		SYNTAX INTEGER {
			normal(0),
			alarm(1) }
		MAX-ACCESS read-only
		STATUS current
		DESCRIPTION
		"upsApm160snmp_1311_DCBusOvervoltage status."
		::= { upsApm160snmpEntry 1311 }
upsApm160snmp_1312_MonCANCommunicationAbnormalR OBJECT-TYPE
		SYNTAX INTEGER {
			normal(0),
			alarm(1) }
		MAX-ACCESS read-only
		STATUS current
		DESCRIPTION
		"upsApm160snmp_1312_MonCANCommunicationAbnormalR status."
		::= { upsApm160snmpEntry 1312 }
upsApm160snmp_1313_MonCANCommunicationAbnormal OBJECT-TYPE
		SYNTAX INTEGER {
			normal(0),
			alarm(1) }
		MAX-ACCESS read-only
		STATUS current
		DESCRIPTION
		"upsApm160snmp_1313_MonCANCommunicationAbnormal status."
		::= { upsApm160snmpEntry 1313 }
upsApm160snmp_1314_InputNeutralLostRecovered OBJECT-TYPE
		SYNTAX INTEGER {
			normal(0),
			alarm(1) }
		MAX-ACCESS read-only
		STATUS current
		DESCRIPTION
		"upsApm160snmp_1314_InputNeutralLostRecovered status."
		::= { upsApm160snmpEntry 1314 }
upsApm160snmp_1315_InputNeutralLost OBJECT-TYPE
		SYNTAX INTEGER {
			normal(0),
			alarm(1) }
		MAX-ACCESS read-only
		STATUS current
		DESCRIPTION
		"upsApm160snmp_1315_InputNeutralLost status."
		::= { upsApm160snmpEntry 1315 }
upsApm160snmp_1316_InverterRelayFailRecovered OBJECT-TYPE
		SYNTAX INTEGER {
			normal(0),
			alarm(1) }
		MAX-ACCESS read-only
		STATUS current
		DESCRIPTION
		"upsApm160snmp_1316_InverterRelayFailRecovered status."
		::= { upsApm160snmpEntry 1316 }
upsApm160snmp_1317_InverterRelayFail OBJECT-TYPE
		SYNTAX INTEGER {
			normal(0),
			alarm(1) }
		MAX-ACCESS read-only
		STATUS current
		DESCRIPTION
		"upsApm160snmp_1317_InverterRelayFail status."
		::= { upsApm160snmpEntry 1317 }
upsApm160snmp_1318_InputBackfeedRecovered OBJECT-TYPE
		SYNTAX INTEGER {
			normal(0),
			alarm(1) }
		MAX-ACCESS read-only
		STATUS current
		DESCRIPTION
		"upsApm160snmp_1318_InputBackfeedRecovered status."
		::= { upsApm160snmpEntry 1318 }
upsApm160snmp_1319_InputBackfeed OBJECT-TYPE
		SYNTAX INTEGER {
			normal(0),
			alarm(1) }
		MAX-ACCESS read-only
		STATUS current
		DESCRIPTION
		"upsApm160snmp_1319_InputBackfeed status."
		::= { upsApm160snmpEntry 1319 }
upsApm160snmp_1320_InputCurrentAbnormalRecovere OBJECT-TYPE
		SYNTAX INTEGER {
			normal(0),
			alarm(1) }
		MAX-ACCESS read-only
		STATUS current
		DESCRIPTION
		"upsApm160snmp_1320_InputCurrentAbnormalRecovere status."
		::= { upsApm160snmpEntry 1320 }
upsApm160snmp_1321_InputCurrentAbnormal OBJECT-TYPE
		SYNTAX INTEGER {
			normal(0),
			alarm(1) }
		MAX-ACCESS read-only
		STATUS current
		DESCRIPTION
		"upsApm160snmp_1321_InputCurrentAbnormal status."
		::= { upsApm160snmpEntry 1321 }
upsApm160snmp_1322_OutputVoltageAbnormalRecover OBJECT-TYPE
		SYNTAX INTEGER {
			normal(0),
			alarm(1) }
		MAX-ACCESS read-only
		STATUS current
		DESCRIPTION
		"upsApm160snmp_1322_OutputVoltageAbnormalRecover status."
		::= { upsApm160snmpEntry 1322 }
upsApm160snmp_1323_OutputVoltageAbnormal OBJECT-TYPE
		SYNTAX INTEGER {
			normal(0),
			alarm(1) }
		MAX-ACCESS read-only
		STATUS current
		DESCRIPTION
		"upsApm160snmp_1323_OutputVoltageAbnormal status."
		::= { upsApm160snmpEntry 1323 }
upsApm160snmp_1324_InputCurrentLimitRecovered OBJECT-TYPE
		SYNTAX INTEGER {
			normal(0),
			alarm(1) }
		MAX-ACCESS read-only
		STATUS current
		DESCRIPTION
		"upsApm160snmp_1324_InputCurrentLimitRecovered status."
		::= { upsApm160snmpEntry 1324 }
upsApm160snmp_1325_InputCurrentLimit OBJECT-TYPE
		SYNTAX INTEGER {
			normal(0),
			alarm(1) }
		MAX-ACCESS read-only
		STATUS current
		DESCRIPTION
		"upsApm160snmp_1325_InputCurrentLimit status."
		::= { upsApm160snmpEntry 1325 }
upsApm160snmp_1326_BypassOvertemperature OBJECT-TYPE
		SYNTAX INTEGER {
			normal(0),
			alarm(1) }
		MAX-ACCESS read-only
		STATUS current
		DESCRIPTION
		"upsApm160snmp_1326_BypassOvertemperature status."
		::= { upsApm160snmpEntry 1326 }
upsApm160snmp_1327_BypassOvertemperature OBJECT-TYPE
		SYNTAX INTEGER {
			normal(0),
			alarm(1) }
		MAX-ACCESS read-only
		STATUS current
		DESCRIPTION
		"upsApm160snmp_1327_BypassOvertemperature status."
		::= { upsApm160snmpEntry 1327 }
upsApm160snmp_1328_OtherBypassSTSFailRecovered OBJECT-TYPE
		SYNTAX INTEGER {
			normal(0),
			alarm(1) }
		MAX-ACCESS read-only
		STATUS current
		DESCRIPTION
		"upsApm160snmp_1328_OtherBypassSTSFailRecovered status."
		::= { upsApm160snmpEntry 1328 }
upsApm160snmp_1329_OtherBypassSTSFail OBJECT-TYPE
		SYNTAX INTEGER {
			normal(0),
			alarm(1) }
		MAX-ACCESS read-only
		STATUS current
		DESCRIPTION
		"upsApm160snmp_1329_OtherBypassSTSFail status."
		::= { upsApm160snmpEntry 1329 }
upsApm160snmp_1330_ParallelCableAbnormalRecover OBJECT-TYPE
		SYNTAX INTEGER {
			normal(0),
			alarm(1) }
		MAX-ACCESS read-only
		STATUS current
		DESCRIPTION
		"upsApm160snmp_1330_ParallelCableAbnormalRecover status."
		::= { upsApm160snmpEntry 1330 }
upsApm160snmp_1331_ParallelCableAbnormal OBJECT-TYPE
		SYNTAX INTEGER {
			normal(0),
			alarm(1) }
		MAX-ACCESS read-only
		STATUS current
		DESCRIPTION
		"upsApm160snmp_1331_ParallelCableAbnormal status."
		::= { upsApm160snmpEntry 1331 }
upsApm160snmp_1332_ChargerOvertemperatureRecover OBJECT-TYPE
		SYNTAX INTEGER {
			normal(0),
			alarm(1) }
		MAX-ACCESS read-only
		STATUS current
		DESCRIPTION
		"upsApm160snmp_1332_ChargerOvertemperatureRecover status."
		::= { upsApm160snmpEntry 1332 }
upsApm160snmp_1333_ChargerOvertemperature OBJECT-TYPE
		SYNTAX INTEGER {
			normal(0),
			alarm(1) }
		MAX-ACCESS read-only
		STATUS current
		DESCRIPTION
		"upsApm160snmp_1333_ChargerOvertemperature status."
		::= { upsApm160snmpEntry 1333 }
upsApm160snmp_1334_BatteryTerminalShortRecovere OBJECT-TYPE
		SYNTAX INTEGER {
			normal(0),
			alarm(1) }
		MAX-ACCESS read-only
		STATUS current
		DESCRIPTION
		"upsApm160snmp_1334_BatteryTerminalShortRecovere status."
		::= { upsApm160snmpEntry 1334 }
upsApm160snmp_1335_BatteryTerminalShort OBJECT-TYPE
		SYNTAX INTEGER {
			normal(0),
			alarm(1) }
		MAX-ACCESS read-only
		STATUS current
		DESCRIPTION
		"upsApm160snmp_1335_BatteryTerminalShort status."
		::= { upsApm160snmpEntry 1335 }
upsApm160snmp_1336_BatteryRoomTemperatureAbnorm OBJECT-TYPE
		SYNTAX INTEGER {
			normal(0),
			alarm(1) }
		MAX-ACCESS read-only
		STATUS current
		DESCRIPTION
		"upsApm160snmp_1336_BatteryRoomTemperatureAbnorm status."
		::= { upsApm160snmpEntry 1336 }
upsApm160snmp_1337_BatteryRoomTemperatureAbnorm OBJECT-TYPE
		SYNTAX INTEGER {
			normal(0),
			alarm(1) }
		MAX-ACCESS read-only
		STATUS current
		DESCRIPTION
		"upsApm160snmp_1337_BatteryRoomTemperatureAbnorm status."
		::= { upsApm160snmpEntry 1337 }
upsApm160snmp_1338_FanAbnormalRecovered OBJECT-TYPE
		SYNTAX INTEGER {
			normal(0),
			alarm(1) }
		MAX-ACCESS read-only
		STATUS current
		DESCRIPTION
		"upsApm160snmp_1338_FanAbnormalRecovered status."
		::= { upsApm160snmpEntry 1338 }
upsApm160snmp_1339_FanAbnormal OBJECT-TYPE
		SYNTAX INTEGER {
			normal(0),
			alarm(1) }
		MAX-ACCESS read-only
		STATUS current
		DESCRIPTION
		"upsApm160snmp_1339_FanAbnormal status."
		::= { upsApm160snmpEntry 1339 }
upsApm160snmp_1340_BypassinChargeRecovered OBJECT-TYPE
		SYNTAX INTEGER {
			normal(0),
			alarm(1) }
		MAX-ACCESS read-only
		STATUS current
		DESCRIPTION
		"upsApm160snmp_1340_BypassinChargeRecovered status."
		::= { upsApm160snmpEntry 1340 }
upsApm160snmp_1341_BypassinCharge OBJECT-TYPE
		SYNTAX INTEGER {
			normal(0),
			alarm(1) }
		MAX-ACCESS read-only
		STATUS current
		DESCRIPTION
		"upsApm160snmp_1341_BypassinCharge status."
		::= { upsApm160snmpEntry 1341 }
upsApm160snmp_1342_BCBStatusAbnormalRecovered OBJECT-TYPE
		SYNTAX INTEGER {
			normal(0),
			alarm(1) }
		MAX-ACCESS read-only
		STATUS current
		DESCRIPTION
		"upsApm160snmp_1342_BCBStatusAbnormalRecovered status."
		::= { upsApm160snmpEntry 1342 }
upsApm160snmp_1343_BCBStatusAbnormal OBJECT-TYPE
		SYNTAX INTEGER {
			normal(0),
			alarm(1) }
		MAX-ACCESS read-only
		STATUS current
		DESCRIPTION
		"upsApm160snmp_1343_BCBStatusAbnormal status."
		::= { upsApm160snmpEntry 1343 }
upsApm160snmp_1344_BypassModuleUnauthorizedReco OBJECT-TYPE
		SYNTAX INTEGER {
			normal(0),
			alarm(1) }
		MAX-ACCESS read-only
		STATUS current
		DESCRIPTION
		"upsApm160snmp_1344_BypassModuleUnauthorizedReco status."
		::= { upsApm160snmpEntry 1344 }
upsApm160snmp_1345_BypassModuleUnauthorized OBJECT-TYPE
		SYNTAX INTEGER {
			normal(0),
			alarm(1) }
		MAX-ACCESS read-only
		STATUS current
		DESCRIPTION
		"upsApm160snmp_1345_BypassModuleUnauthorized status."
		::= { upsApm160snmpEntry 1345 }
upsApm160snmp_1346_PowerModuleUnauthorizedRecov OBJECT-TYPE
		SYNTAX INTEGER {
			normal(0),
			alarm(1) }
		MAX-ACCESS read-only
		STATUS current
		DESCRIPTION
		"upsApm160snmp_1346_PowerModuleUnauthorizedRecov status."
		::= { upsApm160snmpEntry 1346 }
upsApm160snmp_1347_PowerModuleUnauthorized OBJECT-TYPE
		SYNTAX INTEGER {
			normal(0),
			alarm(1) }
		MAX-ACCESS read-only
		STATUS current
		DESCRIPTION
		"upsApm160snmp_1347_PowerModuleUnauthorized status."
		::= { upsApm160snmpEntry 1347 }
upsApm160snmp_1348_HMIUnauthorizedRecovered OBJECT-TYPE
		SYNTAX INTEGER {
			normal(0),
			alarm(1) }
		MAX-ACCESS read-only
		STATUS current
		DESCRIPTION
		"upsApm160snmp_1348_HMIUnauthorizedRecovered status."
		::= { upsApm160snmpEntry 1348 }
upsApm160snmp_1349_HMIUnauthorized OBJECT-TYPE
		SYNTAX INTEGER {
			normal(0),
			alarm(1) }
		MAX-ACCESS read-only
		STATUS current
		DESCRIPTION
		"upsApm160snmp_1349_HMIUnauthorized status."
		::= { upsApm160snmpEntry 1349 }
upsApm160snmp_1350_BypassSCRFanAbnormalRecover OBJECT-TYPE
		SYNTAX INTEGER {
			normal(0),
			alarm(1) }
		MAX-ACCESS read-only
		STATUS current
		DESCRIPTION
		"upsApm160snmp_1350_BypassSCRFanAbnormalRecover status."
		::= { upsApm160snmpEntry 1350 }
upsApm160snmp_1351_BypassSCRFanAbnormal OBJECT-TYPE
		SYNTAX INTEGER {
			normal(0),
			alarm(1) }
		MAX-ACCESS read-only
		STATUS current
		DESCRIPTION
		"upsApm160snmp_1351_BypassSCRFanAbnormal status."
		::= { upsApm160snmpEntry 1351 }
upsApm160snmp_1352_BalancerFaultRecovered OBJECT-TYPE
		SYNTAX INTEGER {
			normal(0),
			alarm(1) }
		MAX-ACCESS read-only
		STATUS current
		DESCRIPTION
		"upsApm160snmp_1352_BalancerFaultRecovered status."
		::= { upsApm160snmpEntry 1352 }
upsApm160snmp_1353_BalancerFault OBJECT-TYPE
		SYNTAX INTEGER {
			normal(0),
			alarm(1) }
		MAX-ACCESS read-only
		STATUS current
		DESCRIPTION
		"upsApm160snmp_1353_BalancerFault status."
		::= { upsApm160snmpEntry 1353 }
upsApm160snmp_1354_BalancerOvercurrentRecovered OBJECT-TYPE
		SYNTAX INTEGER {
			normal(0),
			alarm(1) }
		MAX-ACCESS read-only
		STATUS current
		DESCRIPTION
		"upsApm160snmp_1354_BalancerOvercurrentRecovered status."
		::= { upsApm160snmpEntry 1354 }
upsApm160snmp_1355_BalancerOvercurrent OBJECT-TYPE
		SYNTAX INTEGER {
			normal(0),
			alarm(1) }
		MAX-ACCESS read-only
		STATUS current
		DESCRIPTION
		"upsApm160snmp_1355_BalancerOvercurrent status."
		::= { upsApm160snmpEntry 1355 }
upsApm160snmp_1356_BalancerOvertemperatureRecove OBJECT-TYPE
		SYNTAX INTEGER {
			normal(0),
			alarm(1) }
		MAX-ACCESS read-only
		STATUS current
		DESCRIPTION
		"upsApm160snmp_1356_BalancerOvertemperatureRecove status."
		::= { upsApm160snmpEntry 1356 }
upsApm160snmp_1357_BalancerOvertemperature OBJECT-TYPE
		SYNTAX INTEGER {
			normal(0),
			alarm(1) }
		MAX-ACCESS read-only
		STATUS current
		DESCRIPTION
		"upsApm160snmp_1357_BalancerOvertemperature status."
		::= { upsApm160snmpEntry 1357 }
upsApm160snmp_1358_LossofRedundancyRecovered OBJECT-TYPE
		SYNTAX INTEGER {
			normal(0),
			alarm(1) }
		MAX-ACCESS read-only
		STATUS current
		DESCRIPTION
		"upsApm160snmp_1358_LossofRedundancyRecovered status."
		::= { upsApm160snmpEntry 1358 }
upsApm160snmp_1359_LossofRedundancy OBJECT-TYPE
		SYNTAX INTEGER {
			normal(0),
			alarm(1) }
		MAX-ACCESS read-only
		STATUS current
		DESCRIPTION
		"upsApm160snmp_1359_LossofRedundancy status."
		::= { upsApm160snmpEntry 1359 }
upsApm160snmp_1360_PowerHardwareMismatchRecover OBJECT-TYPE
		SYNTAX INTEGER {
			normal(0),
			alarm(1) }
		MAX-ACCESS read-only
		STATUS current
		DESCRIPTION
		"upsApm160snmp_1360_PowerHardwareMismatchRecover status."
		::= { upsApm160snmpEntry 1360 }
upsApm160snmp_1361_PowerHardwareMismatch OBJECT-TYPE
		SYNTAX INTEGER {
			normal(0),
			alarm(1) }
		MAX-ACCESS read-only
		STATUS current
		DESCRIPTION
		"upsApm160snmp_1361_PowerHardwareMismatch status."
		::= { upsApm160snmpEntry 1361 }
upsApm160snmp_1362_ModuleNotReadyRecovered OBJECT-TYPE
		SYNTAX INTEGER {
			normal(0),
			alarm(1) }
		MAX-ACCESS read-only
		STATUS current
		DESCRIPTION
		"upsApm160snmp_1362_ModuleNotReadyRecovered status."
		::= { upsApm160snmpEntry 1362 }
upsApm160snmp_1363_ModuleNotReady OBJECT-TYPE
		SYNTAX INTEGER {
			normal(0),
			alarm(1) }
		MAX-ACCESS read-only
		STATUS current
		DESCRIPTION
		"upsApm160snmp_1363_ModuleNotReady status."
		::= { upsApm160snmpEntry 1363 }
upsApm160snmp_1364_TopoutletFanAbnormalRecover OBJECT-TYPE
		SYNTAX INTEGER {
			normal(0),
			alarm(1) }
		MAX-ACCESS read-only
		STATUS current
		DESCRIPTION
		"upsApm160snmp_1364_TopoutletFanAbnormalRecover status."
		::= { upsApm160snmpEntry 1364 }
upsApm160snmp_1365_TopoutletFanAbnormal OBJECT-TYPE
		SYNTAX INTEGER {
			normal(0),
			alarm(1) }
		MAX-ACCESS read-only
		STATUS current
		DESCRIPTION
		"upsApm160snmp_1365_TopoutletFanAbnormal status."
		::= { upsApm160snmpEntry 1365 }
upsApm160snmp_1366_PhaseAOutputFuseFailRecove OBJECT-TYPE
		SYNTAX INTEGER {
			normal(0),
			alarm(1) }
		MAX-ACCESS read-only
		STATUS current
		DESCRIPTION
		"upsApm160snmp_1366_PhaseAOutputFuseFailRecove status."
		::= { upsApm160snmpEntry 1366 }
upsApm160snmp_1367_PhaseAOutputFuseFail OBJECT-TYPE
		SYNTAX INTEGER {
			normal(0),
			alarm(1) }
		MAX-ACCESS read-only
		STATUS current
		DESCRIPTION
		"upsApm160snmp_1367_PhaseAOutputFuseFail status."
		::= { upsApm160snmpEntry 1367 }
upsApm160snmp_1368_PhaseBOutputFuseFailRecove OBJECT-TYPE
		SYNTAX INTEGER {
			normal(0),
			alarm(1) }
		MAX-ACCESS read-only
		STATUS current
		DESCRIPTION
		"upsApm160snmp_1368_PhaseBOutputFuseFailRecove status."
		::= { upsApm160snmpEntry 1368 }
upsApm160snmp_1369_PhaseBOutputFuseFail OBJECT-TYPE
		SYNTAX INTEGER {
			normal(0),
			alarm(1) }
		MAX-ACCESS read-only
		STATUS current
		DESCRIPTION
		"upsApm160snmp_1369_PhaseBOutputFuseFail status."
		::= { upsApm160snmpEntry 1369 }
upsApm160snmp_1370_PhaseCOutputFuseFailRecove OBJECT-TYPE
		SYNTAX INTEGER {
			normal(0),
			alarm(1) }
		MAX-ACCESS read-only
		STATUS current
		DESCRIPTION
		"upsApm160snmp_1370_PhaseCOutputFuseFailRecove status."
		::= { upsApm160snmpEntry 1370 }
upsApm160snmp_1371_PhaseCOutputFuseFail OBJECT-TYPE
		SYNTAX INTEGER {
			normal(0),
			alarm(1) }
		MAX-ACCESS read-only
		STATUS current
		DESCRIPTION
		"upsApm160snmp_1371_PhaseCOutputFuseFail status."
		::= { upsApm160snmpEntry 1371 }
upsApm160snmp_1372_ParameterConfigurationFailRe OBJECT-TYPE
		SYNTAX INTEGER {
			normal(0),
			alarm(1) }
		MAX-ACCESS read-only
		STATUS current
		DESCRIPTION
		"upsApm160snmp_1372_ParameterConfigurationFailRe status."
		::= { upsApm160snmpEntry 1372 }
upsApm160snmp_1373_ParameterConfigurationFail OBJECT-TYPE
		SYNTAX INTEGER {
			normal(0),
			alarm(1) }
		MAX-ACCESS read-only
		STATUS current
		DESCRIPTION
		"upsApm160snmp_1373_ParameterConfigurationFail status."
		::= { upsApm160snmpEntry 1373 }
upsApm160snmp_1374_BypassOvercurrentTimeoutReco OBJECT-TYPE
		SYNTAX INTEGER {
			normal(0),
			alarm(1) }
		MAX-ACCESS read-only
		STATUS current
		DESCRIPTION
		"upsApm160snmp_1374_BypassOvercurrentTimeoutReco status."
		::= { upsApm160snmpEntry 1374 }
upsApm160snmp_1375_BypassOvercurrentTimeout OBJECT-TYPE
		SYNTAX INTEGER {
			normal(0),
			alarm(1) }
		MAX-ACCESS read-only
		STATUS current
		DESCRIPTION
		"upsApm160snmp_1375_BypassOvercurrentTimeout status."
		::= { upsApm160snmpEntry 1375 }
upsApm160snmp_1376_OvervoltageNGNDRecovered OBJECT-TYPE
		SYNTAX INTEGER {
			normal(0),
			alarm(1) }
		MAX-ACCESS read-only
		STATUS current
		DESCRIPTION
		"upsApm160snmp_1376_OvervoltageNGNDRecovered status."
		::= { upsApm160snmpEntry 1376 }
upsApm160snmp_1377_OvervoltageNGND OBJECT-TYPE
		SYNTAX INTEGER {
			normal(0),
			alarm(1) }
		MAX-ACCESS read-only
		STATUS current
		DESCRIPTION
		"upsApm160snmp_1377_OvervoltageNGND status."
		::= { upsApm160snmpEntry 1377 }
upsApm160snmp_1378_BypassNotAvailableRecovered OBJECT-TYPE
		SYNTAX INTEGER {
			normal(0),
			alarm(1) }
		MAX-ACCESS read-only
		STATUS current
		DESCRIPTION
		"upsApm160snmp_1378_BypassNotAvailableRecovered status."
		::= { upsApm160snmpEntry 1378 }
upsApm160snmp_1379_BypassNotAvailable OBJECT-TYPE
		SYNTAX INTEGER {
			normal(0),
			alarm(1) }
		MAX-ACCESS read-only
		STATUS current
		DESCRIPTION
		"upsApm160snmp_1379_BypassNotAvailable status."
		::= { upsApm160snmpEntry 1379 }
upsApm160snmp_1380_OutputTransformerOvertemperat OBJECT-TYPE
		SYNTAX INTEGER {
			normal(0),
			alarm(1) }
		MAX-ACCESS read-only
		STATUS current
		DESCRIPTION
		"upsApm160snmp_1380_OutputTransformerOvertemperat status."
		::= { upsApm160snmpEntry 1380 }
upsApm160snmp_1381_OutputTransformerOvertemperat OBJECT-TYPE
		SYNTAX INTEGER {
			normal(0),
			alarm(1) }
		MAX-ACCESS read-only
		STATUS current
		DESCRIPTION
		"upsApm160snmp_1381_OutputTransformerOvertemperat status."
		::= { upsApm160snmpEntry 1381 }
upsApm160snmp_1382_OutputFuseFailRecovered OBJECT-TYPE
		SYNTAX INTEGER {
			normal(0),
			alarm(1) }
		MAX-ACCESS read-only
		STATUS current
		DESCRIPTION
		"upsApm160snmp_1382_OutputFuseFailRecovered status."
		::= { upsApm160snmpEntry 1382 }
upsApm160snmp_1383_OutputFuseFail OBJECT-TYPE
		SYNTAX INTEGER {
			normal(0),
			alarm(1) }
		MAX-ACCESS read-only
		STATUS current
		DESCRIPTION
		"upsApm160snmp_1383_OutputFuseFail status."
		::= { upsApm160snmpEntry 1383 }
upsApm160snmp_1384_BatteryTestFailRecovered OBJECT-TYPE
		SYNTAX INTEGER {
			normal(0),
			alarm(1) }
		MAX-ACCESS read-only
		STATUS current
		DESCRIPTION
		"upsApm160snmp_1384_BatteryTestFailRecovered status."
		::= { upsApm160snmpEntry 1384 }
upsApm160snmp_1385_BatteryTestFail OBJECT-TYPE
		SYNTAX INTEGER {
			normal(0),
			alarm(1) }
		MAX-ACCESS read-only
		STATUS current
		DESCRIPTION
		"upsApm160snmp_1385_BatteryTestFail status."
		::= { upsApm160snmpEntry 1385 }
upsApm160snmp_1386_LoadShedSignal1NotActive OBJECT-TYPE
		SYNTAX INTEGER {
			normal(0),
			alarm(1) }
		MAX-ACCESS read-only
		STATUS current
		DESCRIPTION
		"upsApm160snmp_1386_LoadShedSignal1NotActive status."
		::= { upsApm160snmpEntry 1386 }
upsApm160snmp_1387_LoadShedSignal1Active OBJECT-TYPE
		SYNTAX INTEGER {
			normal(0),
			alarm(1) }
		MAX-ACCESS read-only
		STATUS current
		DESCRIPTION
		"upsApm160snmp_1387_LoadShedSignal1Active status."
		::= { upsApm160snmpEntry 1387 }
upsApm160snmp_1388_LoadShedSignal2NotActive OBJECT-TYPE
		SYNTAX INTEGER {
			normal(0),
			alarm(1) }
		MAX-ACCESS read-only
		STATUS current
		DESCRIPTION
		"upsApm160snmp_1388_LoadShedSignal2NotActive status."
		::= { upsApm160snmpEntry 1388 }
upsApm160snmp_1389_LoadShedSignal2Active OBJECT-TYPE
		SYNTAX INTEGER {
			normal(0),
			alarm(1) }
		MAX-ACCESS read-only
		STATUS current
		DESCRIPTION
		"upsApm160snmp_1389_LoadShedSignal2Active status."
		::= { upsApm160snmpEntry 1389 }
upsApm160snmp_1390_BypassModuleAvailable OBJECT-TYPE
		SYNTAX INTEGER {
			normal(0),
			alarm(1) }
		MAX-ACCESS read-only
		STATUS current
		DESCRIPTION
		"upsApm160snmp_1390_BypassModuleAvailable status."
		::= { upsApm160snmpEntry 1390 }
upsApm160snmp_1391_BypassModuleNotAvailable OBJECT-TYPE
		SYNTAX INTEGER {
			normal(0),
			alarm(1) }
		MAX-ACCESS read-only
		STATUS current
		DESCRIPTION
		"upsApm160snmp_1391_BypassModuleNotAvailable status."
		::= { upsApm160snmpEntry 1391 }
upsApm160snmp_1392_ControlModuleAvailable OBJECT-TYPE
		SYNTAX INTEGER {
			normal(0),
			alarm(1) }
		MAX-ACCESS read-only
		STATUS current
		DESCRIPTION
		"upsApm160snmp_1392_ControlModuleAvailable status."
		::= { upsApm160snmpEntry 1392 }
upsApm160snmp_1393_ControlModuleNotAvailable OBJECT-TYPE
		SYNTAX INTEGER {
			normal(0),
			alarm(1) }
		MAX-ACCESS read-only
		STATUS current
		DESCRIPTION
		"upsApm160snmp_1393_ControlModuleNotAvailable status."
		::= { upsApm160snmpEntry 1393 }
upsApm160snmp_1394_SystemMainsFuseNormal OBJECT-TYPE
		SYNTAX INTEGER {
			normal(0),
			alarm(1) }
		MAX-ACCESS read-only
		STATUS current
		DESCRIPTION
		"upsApm160snmp_1394_SystemMainsFuseNormal status."
		::= { upsApm160snmpEntry 1394 }
upsApm160snmp_1395_SystemMainsFuseFail OBJECT-TYPE
		SYNTAX INTEGER {
			normal(0),
			alarm(1) }
		MAX-ACCESS read-only
		STATUS current
		DESCRIPTION
		"upsApm160snmp_1395_SystemMainsFuseFail status."
		::= { upsApm160snmpEntry 1395 }
upsApm160snmp_1396_BypassFuseNormal OBJECT-TYPE
		SYNTAX INTEGER {
			normal(0),
			alarm(1) }
		MAX-ACCESS read-only
		STATUS current
		DESCRIPTION
		"upsApm160snmp_1396_BypassFuseNormal status."
		::= { upsApm160snmpEntry 1396 }
upsApm160snmp_1397_BypassFuseFail OBJECT-TYPE
		SYNTAX INTEGER {
			normal(0),
			alarm(1) }
		MAX-ACCESS read-only
		STATUS current
		DESCRIPTION
		"upsApm160snmp_1397_BypassFuseFail status."
		::= { upsApm160snmpEntry 1397 }
upsApm160snmp_1398_SystemOutputFuseNormal OBJECT-TYPE
		SYNTAX INTEGER {
			normal(0),
			alarm(1) }
		MAX-ACCESS read-only
		STATUS current
		DESCRIPTION
		"upsApm160snmp_1398_SystemOutputFuseNormal status."
		::= { upsApm160snmpEntry 1398 }
upsApm160snmp_1399_SystemOutputFuseFail OBJECT-TYPE
		SYNTAX INTEGER {
			normal(0),
			alarm(1) }
		MAX-ACCESS read-only
		STATUS current
		DESCRIPTION
		"upsApm160snmp_1399_SystemOutputFuseFail status."
		::= { upsApm160snmpEntry 1399 }
upsApm160snmp_1400_LoadonMaintainaceBypassNorm OBJECT-TYPE
		SYNTAX INTEGER {
			normal(0),
			alarm(1) }
		MAX-ACCESS read-only
		STATUS current
		DESCRIPTION
		"upsApm160snmp_1400_LoadonMaintainaceBypassNorm status."
		::= { upsApm160snmpEntry 1400 }
upsApm160snmp_1401_LoadonMaintainaceBypass OBJECT-TYPE
		SYNTAX INTEGER {
			normal(0),
			alarm(1) }
		MAX-ACCESS read-only
		STATUS current
		DESCRIPTION
		"upsApm160snmp_1401_LoadonMaintainaceBypass status."
		::= { upsApm160snmpEntry 1401 }
upsApm160snmp_1402_Outputnormal OBJECT-TYPE
		SYNTAX INTEGER {
			normal(0),
			alarm(1) }
		MAX-ACCESS read-only
		STATUS current
		DESCRIPTION
		"upsApm160snmp_1402_Outputnormal status."
		::= { upsApm160snmpEntry 1402 }
upsApm160snmp_1403_Outputshort OBJECT-TYPE
		SYNTAX INTEGER {
			normal(0),
			alarm(1) }
		MAX-ACCESS read-only
		STATUS current
		DESCRIPTION
		"upsApm160snmp_1403_Outputshort status."
		::= { upsApm160snmpEntry 1403 }
upsApm160snmp_1404_Batterynormal OBJECT-TYPE
		SYNTAX INTEGER {
			normal(0),
			alarm(1) }
		MAX-ACCESS read-only
		STATUS current
		DESCRIPTION
		"upsApm160snmp_1404_Batterynormal status."
		::= { upsApm160snmpEntry 1404 }
upsApm160snmp_1405_BatteryDeepDischargeAlarm OBJECT-TYPE
		SYNTAX INTEGER {
			normal(0),
			alarm(1) }
		MAX-ACCESS read-only
		STATUS current
		DESCRIPTION
		"upsApm160snmp_1405_BatteryDeepDischargeAlarm status."
		::= { upsApm160snmpEntry 1405 }
upsApm160snmp_1406_LoadonBypassUnionRecovered OBJECT-TYPE
		SYNTAX INTEGER {
			normal(0),
			alarm(1) }
		MAX-ACCESS read-only
		STATUS current
		DESCRIPTION
		"upsApm160snmp_1406_LoadonBypassUnionRecovered status."
		::= { upsApm160snmpEntry 1406 }
upsApm160snmp_1407_LoadonBypassUnion OBJECT-TYPE
		SYNTAX INTEGER {
			normal(0),
			alarm(1) }
		MAX-ACCESS read-only
		STATUS current
		DESCRIPTION
		"upsApm160snmp_1407_LoadonBypassUnion status."
		::= { upsApm160snmpEntry 1407 }
upsApm160snmp_1408_SPMInternalCommFailureRecov OBJECT-TYPE
		SYNTAX INTEGER {
			normal(0),
			alarm(1) }
		MAX-ACCESS read-only
		STATUS current
		DESCRIPTION
		"upsApm160snmp_1408_SPMInternalCommFailureRecov status."
		::= { upsApm160snmpEntry 1408 }
upsApm160snmp_1409_SPMInternalCommFailure OBJECT-TYPE
		SYNTAX INTEGER {
			normal(0),
			alarm(1) }
		MAX-ACCESS read-only
		STATUS current
		DESCRIPTION
		"upsApm160snmp_1409_SPMInternalCommFailure status."
		::= { upsApm160snmpEntry 1409 }
upsApm160snmp_1410_SPD1BreakerOpenRecovered OBJECT-TYPE
		SYNTAX INTEGER {
			normal(0),
			alarm(1) }
		MAX-ACCESS read-only
		STATUS current
		DESCRIPTION
		"upsApm160snmp_1410_SPD1BreakerOpenRecovered status."
		::= { upsApm160snmpEntry 1410 }
upsApm160snmp_1411_SPD1BreakerOpen OBJECT-TYPE
		SYNTAX INTEGER {
			normal(0),
			alarm(1) }
		MAX-ACCESS read-only
		STATUS current
		DESCRIPTION
		"upsApm160snmp_1411_SPD1BreakerOpen status."
		::= { upsApm160snmpEntry 1411 }
upsApm160snmp_1412_SPD1OpenRecovered OBJECT-TYPE
		SYNTAX INTEGER {
			normal(0),
			alarm(1) }
		MAX-ACCESS read-only
		STATUS current
		DESCRIPTION
		"upsApm160snmp_1412_SPD1OpenRecovered status."
		::= { upsApm160snmpEntry 1412 }
upsApm160snmp_1413_SPD1Open OBJECT-TYPE
		SYNTAX INTEGER {
			normal(0),
			alarm(1) }
		MAX-ACCESS read-only
		STATUS current
		DESCRIPTION
		"upsApm160snmp_1413_SPD1Open status."
		::= { upsApm160snmpEntry 1413 }
upsApm160snmp_1414_SPD2BreakerOpenRecovered OBJECT-TYPE
		SYNTAX INTEGER {
			normal(0),
			alarm(1) }
		MAX-ACCESS read-only
		STATUS current
		DESCRIPTION
		"upsApm160snmp_1414_SPD2BreakerOpenRecovered status."
		::= { upsApm160snmpEntry 1414 }
upsApm160snmp_1415_SPD2BreakerOpen OBJECT-TYPE
		SYNTAX INTEGER {
			normal(0),
			alarm(1) }
		MAX-ACCESS read-only
		STATUS current
		DESCRIPTION
		"upsApm160snmp_1415_SPD2BreakerOpen status."
		::= { upsApm160snmpEntry 1415 }
upsApm160snmp_1416_SPD2OpenRecovered OBJECT-TYPE
		SYNTAX INTEGER {
			normal(0),
			alarm(1) }
		MAX-ACCESS read-only
		STATUS current
		DESCRIPTION
		"upsApm160snmp_1416_SPD2OpenRecovered status."
		::= { upsApm160snmpEntry 1416 }
upsApm160snmp_1417_SPD2Open OBJECT-TYPE
		SYNTAX INTEGER {
			normal(0),
			alarm(1) }
		MAX-ACCESS read-only
		STATUS current
		DESCRIPTION
		"upsApm160snmp_1417_SPD2Open status."
		::= { upsApm160snmpEntry 1417 }
upsApm160snmp_1418_Board1Ready OBJECT-TYPE
		SYNTAX INTEGER {
			normal(0),
			alarm(1) }
		MAX-ACCESS read-only
		STATUS current
		DESCRIPTION
		"upsApm160snmp_1418_Board1Ready status."
		::= { upsApm160snmpEntry 1418 }
upsApm160snmp_1419_Board1NotReady OBJECT-TYPE
		SYNTAX INTEGER {
			normal(0),
			alarm(1) }
		MAX-ACCESS read-only
		STATUS current
		DESCRIPTION
		"upsApm160snmp_1419_Board1NotReady status."
		::= { upsApm160snmpEntry 1419 }
upsApm160snmp_1420_Board2Ready OBJECT-TYPE
		SYNTAX INTEGER {
			normal(0),
			alarm(1) }
		MAX-ACCESS read-only
		STATUS current
		DESCRIPTION
		"upsApm160snmp_1420_Board2Ready status."
		::= { upsApm160snmpEntry 1420 }
upsApm160snmp_1421_Board2NotReady OBJECT-TYPE
		SYNTAX INTEGER {
			normal(0),
			alarm(1) }
		MAX-ACCESS read-only
		STATUS current
		DESCRIPTION
		"upsApm160snmp_1421_Board2NotReady status."
		::= { upsApm160snmpEntry 1421 }
upsApm160snmp_1422_Board3Ready OBJECT-TYPE
		SYNTAX INTEGER {
			normal(0),
			alarm(1) }
		MAX-ACCESS read-only
		STATUS current
		DESCRIPTION
		"upsApm160snmp_1422_Board3Ready status."
		::= { upsApm160snmpEntry 1422 }
upsApm160snmp_1423_Board3NotReady OBJECT-TYPE
		SYNTAX INTEGER {
			normal(0),
			alarm(1) }
		MAX-ACCESS read-only
		STATUS current
		DESCRIPTION
		"upsApm160snmp_1423_Board3NotReady status."
		::= { upsApm160snmpEntry 1423 }
upsApm160snmp_1424_Board4Ready OBJECT-TYPE
		SYNTAX INTEGER {
			normal(0),
			alarm(1) }
		MAX-ACCESS read-only
		STATUS current
		DESCRIPTION
		"upsApm160snmp_1424_Board4Ready status."
		::= { upsApm160snmpEntry 1424 }
upsApm160snmp_1425_Board4NotReady OBJECT-TYPE
		SYNTAX INTEGER {
			normal(0),
			alarm(1) }
		MAX-ACCESS read-only
		STATUS current
		DESCRIPTION
		"upsApm160snmp_1425_Board4NotReady status."
		::= { upsApm160snmpEntry 1425 }
upsApm160snmp_1426_Board5Ready OBJECT-TYPE
		SYNTAX INTEGER {
			normal(0),
			alarm(1) }
		MAX-ACCESS read-only
		STATUS current
		DESCRIPTION
		"upsApm160snmp_1426_Board5Ready status."
		::= { upsApm160snmpEntry 1426 }
upsApm160snmp_1427_Board5NotReady OBJECT-TYPE
		SYNTAX INTEGER {
			normal(0),
			alarm(1) }
		MAX-ACCESS read-only
		STATUS current
		DESCRIPTION
		"upsApm160snmp_1427_Board5NotReady status."
		::= { upsApm160snmpEntry 1427 }
upsApm160snmp_1428_Board6Ready OBJECT-TYPE
		SYNTAX INTEGER {
			normal(0),
			alarm(1) }
		MAX-ACCESS read-only
		STATUS current
		DESCRIPTION
		"upsApm160snmp_1428_Board6Ready status."
		::= { upsApm160snmpEntry 1428 }
upsApm160snmp_1429_Board6NotReady OBJECT-TYPE
		SYNTAX INTEGER {
			normal(0),
			alarm(1) }
		MAX-ACCESS read-only
		STATUS current
		DESCRIPTION
		"upsApm160snmp_1429_Board6NotReady status."
		::= { upsApm160snmpEntry 1429 }
upsApm160snmp_1430_Board7Ready OBJECT-TYPE
		SYNTAX INTEGER {
			normal(0),
			alarm(1) }
		MAX-ACCESS read-only
		STATUS current
		DESCRIPTION
		"upsApm160snmp_1430_Board7Ready status."
		::= { upsApm160snmpEntry 1430 }
upsApm160snmp_1431_Board7NotReady OBJECT-TYPE
		SYNTAX INTEGER {
			normal(0),
			alarm(1) }
		MAX-ACCESS read-only
		STATUS current
		DESCRIPTION
		"upsApm160snmp_1431_Board7NotReady status."
		::= { upsApm160snmpEntry 1431 }
upsApm160snmp_1432_Board8Ready OBJECT-TYPE
		SYNTAX INTEGER {
			normal(0),
			alarm(1) }
		MAX-ACCESS read-only
		STATUS current
		DESCRIPTION
		"upsApm160snmp_1432_Board8Ready status."
		::= { upsApm160snmpEntry 1432 }
upsApm160snmp_1433_Board8NotReady OBJECT-TYPE
		SYNTAX INTEGER {
			normal(0),
			alarm(1) }
		MAX-ACCESS read-only
		STATUS current
		DESCRIPTION
		"upsApm160snmp_1433_Board8NotReady status."
		::= { upsApm160snmpEntry 1433 }
upsApm160snmp_1434_Board9Ready OBJECT-TYPE
		SYNTAX INTEGER {
			normal(0),
			alarm(1) }
		MAX-ACCESS read-only
		STATUS current
		DESCRIPTION
		"upsApm160snmp_1434_Board9Ready status."
		::= { upsApm160snmpEntry 1434 }
upsApm160snmp_1435_Board9NotReady OBJECT-TYPE
		SYNTAX INTEGER {
			normal(0),
			alarm(1) }
		MAX-ACCESS read-only
		STATUS current
		DESCRIPTION
		"upsApm160snmp_1435_Board9NotReady status."
		::= { upsApm160snmpEntry 1435 }
upsApm160snmp_1436_Board10Ready OBJECT-TYPE
		SYNTAX INTEGER {
			normal(0),
			alarm(1) }
		MAX-ACCESS read-only
		STATUS current
		DESCRIPTION
		"upsApm160snmp_1436_Board10Ready status."
		::= { upsApm160snmpEntry 1436 }
upsApm160snmp_1437_Board10NotReady OBJECT-TYPE
		SYNTAX INTEGER {
			normal(0),
			alarm(1) }
		MAX-ACCESS read-only
		STATUS current
		DESCRIPTION
		"upsApm160snmp_1437_Board10NotReady status."
		::= { upsApm160snmpEntry 1437 }
upsApm160snmp_1438_Board11Ready OBJECT-TYPE
		SYNTAX INTEGER {
			normal(0),
			alarm(1) }
		MAX-ACCESS read-only
		STATUS current
		DESCRIPTION
		"upsApm160snmp_1438_Board11Ready status."
		::= { upsApm160snmpEntry 1438 }
upsApm160snmp_1439_Board11NotReady OBJECT-TYPE
		SYNTAX INTEGER {
			normal(0),
			alarm(1) }
		MAX-ACCESS read-only
		STATUS current
		DESCRIPTION
		"upsApm160snmp_1439_Board11NotReady status."
		::= { upsApm160snmpEntry 1439 }
upsApm160snmp_1440_Board12Ready OBJECT-TYPE
		SYNTAX INTEGER {
			normal(0),
			alarm(1) }
		MAX-ACCESS read-only
		STATUS current
		DESCRIPTION
		"upsApm160snmp_1440_Board12Ready status."
		::= { upsApm160snmpEntry 1440 }
upsApm160snmp_1441_Board12NotReady OBJECT-TYPE
		SYNTAX INTEGER {
			normal(0),
			alarm(1) }
		MAX-ACCESS read-only
		STATUS current
		DESCRIPTION
		"upsApm160snmp_1441_Board12NotReady status."
		::= { upsApm160snmpEntry 1441 }
upsApm160snmp_1442_Board13Ready OBJECT-TYPE
		SYNTAX INTEGER {
			normal(0),
			alarm(1) }
		MAX-ACCESS read-only
		STATUS current
		DESCRIPTION
		"upsApm160snmp_1442_Board13Ready status."
		::= { upsApm160snmpEntry 1442 }
upsApm160snmp_1443_Board13NotReady OBJECT-TYPE
		SYNTAX INTEGER {
			normal(0),
			alarm(1) }
		MAX-ACCESS read-only
		STATUS current
		DESCRIPTION
		"upsApm160snmp_1443_Board13NotReady status."
		::= { upsApm160snmpEntry 1443 }
upsApm160snmp_1444_Board14Ready OBJECT-TYPE
		SYNTAX INTEGER {
			normal(0),
			alarm(1) }
		MAX-ACCESS read-only
		STATUS current
		DESCRIPTION
		"upsApm160snmp_1444_Board14Ready status."
		::= { upsApm160snmpEntry 1444 }
upsApm160snmp_1445_Board14NotReady OBJECT-TYPE
		SYNTAX INTEGER {
			normal(0),
			alarm(1) }
		MAX-ACCESS read-only
		STATUS current
		DESCRIPTION
		"upsApm160snmp_1445_Board14NotReady status."
		::= { upsApm160snmpEntry 1445 }
upsApm160snmp_1446_Board15Ready OBJECT-TYPE
		SYNTAX INTEGER {
			normal(0),
			alarm(1) }
		MAX-ACCESS read-only
		STATUS current
		DESCRIPTION
		"upsApm160snmp_1446_Board15Ready status."
		::= { upsApm160snmpEntry 1446 }
upsApm160snmp_1447_Board15NotReady OBJECT-TYPE
		SYNTAX INTEGER {
			normal(0),
			alarm(1) }
		MAX-ACCESS read-only
		STATUS current
		DESCRIPTION
		"upsApm160snmp_1447_Board15NotReady status."
		::= { upsApm160snmpEntry 1447 }
upsApm160snmp_1448_Board16Ready OBJECT-TYPE
		SYNTAX INTEGER {
			normal(0),
			alarm(1) }
		MAX-ACCESS read-only
		STATUS current
		DESCRIPTION
		"upsApm160snmp_1448_Board16Ready status."
		::= { upsApm160snmpEntry 1448 }
upsApm160snmp_1449_Board16NotReady OBJECT-TYPE
		SYNTAX INTEGER {
			normal(0),
			alarm(1) }
		MAX-ACCESS read-only
		STATUS current
		DESCRIPTION
		"upsApm160snmp_1449_Board16NotReady status."
		::= { upsApm160snmpEntry 1449 }
upsApm160snmp_1450_SPMCRCCheckErrorRecovered OBJECT-TYPE
		SYNTAX INTEGER {
			normal(0),
			alarm(1) }
		MAX-ACCESS read-only
		STATUS current
		DESCRIPTION
		"upsApm160snmp_1450_SPMCRCCheckErrorRecovered status."
		::= { upsApm160snmpEntry 1450 }
upsApm160snmp_1451_SPMCRCCheckError OBJECT-TYPE
		SYNTAX INTEGER {
			normal(0),
			alarm(1) }
		MAX-ACCESS read-only
		STATUS current
		DESCRIPTION
		"upsApm160snmp_1451_SPMCRCCheckError status."
		::= { upsApm160snmpEntry 1451 }
upsApm160snmp_1452_ExternalInputSwitchRecovered OBJECT-TYPE
		SYNTAX INTEGER {
			normal(0),
			alarm(1) }
		MAX-ACCESS read-only
		STATUS current
		DESCRIPTION
		"upsApm160snmp_1452_ExternalInputSwitchRecovered status."
		::= { upsApm160snmpEntry 1452 }
upsApm160snmp_1453_ExternalInputSwitchOpen OBJECT-TYPE
		SYNTAX INTEGER {
			normal(0),
			alarm(1) }
		MAX-ACCESS read-only
		STATUS current
		DESCRIPTION
		"upsApm160snmp_1453_ExternalInputSwitchOpen status."
		::= { upsApm160snmpEntry 1453 }
upsApm160snmp_1454_ExternalBypassSwitchRecovere OBJECT-TYPE
		SYNTAX INTEGER {
			normal(0),
			alarm(1) }
		MAX-ACCESS read-only
		STATUS current
		DESCRIPTION
		"upsApm160snmp_1454_ExternalBypassSwitchRecovere status."
		::= { upsApm160snmpEntry 1454 }
upsApm160snmp_1455_ExternalBypassSwitchOpen OBJECT-TYPE
		SYNTAX INTEGER {
			normal(0),
			alarm(1) }
		MAX-ACCESS read-only
		STATUS current
		DESCRIPTION
		"upsApm160snmp_1455_ExternalBypassSwitchOpen status."
		::= { upsApm160snmpEntry 1455 }
upsApm160snmp_1456_BranchOverCurrent OBJECT-TYPE
		SYNTAX INTEGER {
			normal(0),
			alarm(1) }
		MAX-ACCESS read-only
		STATUS current
		DESCRIPTION
		"upsApm160snmp_1456_BranchOverCurrent status."
		::= { upsApm160snmpEntry 1456 }
upsApm160snmp_1457_BranchCurrentOverHighLimit OBJECT-TYPE
		SYNTAX INTEGER {
			normal(0),
			alarm(1) }
		MAX-ACCESS read-only
		STATUS current
		DESCRIPTION
		"upsApm160snmp_1457_BranchCurrentOverHighLimit status."
		::= { upsApm160snmpEntry 1457 }
upsApm160snmp_1458_BranchCurrentOverLowLimit OBJECT-TYPE
		SYNTAX INTEGER {
			normal(0),
			alarm(1) }
		MAX-ACCESS read-only
		STATUS current
		DESCRIPTION
		"upsApm160snmp_1458_BranchCurrentOverLowLimit status."
		::= { upsApm160snmpEntry 1458 }
upsApm160snmp_1459_BranchInrushOverCurrent OBJECT-TYPE
		SYNTAX INTEGER {
			normal(0),
			alarm(1) }
		MAX-ACCESS read-only
		STATUS current
		DESCRIPTION
		"upsApm160snmp_1459_BranchInrushOverCurrent status."
		::= { upsApm160snmpEntry 1459 }
upsApm160snmp_1460_BranchBreakerFail OBJECT-TYPE
		SYNTAX INTEGER {
			normal(0),
			alarm(1) }
		MAX-ACCESS read-only
		STATUS current
		DESCRIPTION
		"upsApm160snmp_1460_BranchBreakerFail status."
		::= { upsApm160snmpEntry 1460 }
upsApm160snmp_1461_ParaDiscreteBusCommunicatonN OBJECT-TYPE
		SYNTAX INTEGER {
			normal(0),
			alarm(1) }
		MAX-ACCESS read-only
		STATUS current
		DESCRIPTION
		"upsApm160snmp_1461_ParaDiscreteBusCommunicatonN status."
		::= { upsApm160snmpEntry 1461 }
upsApm160snmp_1462_ParaDiscreteBusCommunicatonA OBJECT-TYPE
		SYNTAX INTEGER {
			normal(0),
			alarm(1) }
		MAX-ACCESS read-only
		STATUS current
		DESCRIPTION
		"upsApm160snmp_1462_ParaDiscreteBusCommunicatonA status."
		::= { upsApm160snmpEntry 1462 }
upsApm160snmp_1463_CommunicateStatus OBJECT-TYPE
		SYNTAX INTEGER {
			normal(0),
			alarm(1) }
		MAX-ACCESS read-only
		STATUS current
		DESCRIPTION
		"upsApm160snmp_1463_CommunicateStatus status."
		::= { upsApm160snmpEntry 1463 }



------------------------------------------------------------
-- System Alarm Trap Table { 13400.3.254 }
------------------------------------------------------------
		
systemAlarmTrapTable OBJECT-TYPE
	SYNTAX SEQUENCE OF SystemAlarmTrapEntry
	MAX-ACCESS not-accessible
	STATUS current
	DESCRIPTION "System Table holding information about the submitted alarm traps."
	::= { dcs 254 }

systemAlarmTrapEntry OBJECT-TYPE
	SYNTAX SystemAlarmTrapEntry
	MAX-ACCESS not-accessible
	STATUS current
	DESCRIPTION "An entry (conceptual row) in the systemAlarmTrapTable."
	INDEX { systemAlarmIndex }
	::= { systemAlarmTrapTable 1 }

SystemAlarmTrapEntry ::= SEQUENCE {
	systemAlarmIndex 			Counter32,
	systemAlarmTime 			DisplayString,
	systemAlarmStatusChange 	AlarmStatusChange,
	systemAlarmSeverity 		AlarmSeverity,
	systemAlarmDescription 		DisplayString,
	systemAlarmId 				Integer32,
	systemAlarmEquipId 			Integer32,
	systemAlarmEquipTypeId		Integer32}

systemAlarmIndex OBJECT-TYPE
	SYNTAX Counter32
	MAX-ACCESS read-only
	STATUS current
	DESCRIPTION "The unique sequence number of this alarm trap."
	::= { systemAlarmTrapEntry 1 }

systemAlarmTime OBJECT-TYPE
	SYNTAX DisplayString
	MAX-ACCESS read-only
	STATUS current
	DESCRIPTION "Local date and time when event occured, format as YYYY-MM-DD hh:mm:ss."
	::= { systemAlarmTrapEntry 2 }

systemAlarmStatusChange OBJECT-TYPE
	SYNTAX AlarmStatusChange
	MAX-ACCESS read-only
	STATUS current
	DESCRIPTION "Indicates 'activated' (0) or 'deactivated' (1) alarm events."
	::= { systemAlarmTrapEntry 3 }

systemAlarmSeverity OBJECT-TYPE
	SYNTAX AlarmSeverity
	MAX-ACCESS read-only
	STATUS current
	DESCRIPTION "The severity of the alarm. One of
		(1) informational
		(2) warning
		(3) critical"
	::= { systemAlarmTrapEntry 4 }
	
systemAlarmDescription OBJECT-TYPE
	SYNTAX DisplayString
	MAX-ACCESS read-only
	STATUS current
	DESCRIPTION "Free-text description of alarm."
	::= { systemAlarmTrapEntry 5 }
	
systemAlarmId OBJECT-TYPE
	SYNTAX Integer32
	MAX-ACCESS read-only
	STATUS current
	DESCRIPTION "Alarm id."
	::= { systemAlarmTrapEntry 6 }
	
systemAlarmEquipId OBJECT-TYPE
	SYNTAX Integer32
	MAX-ACCESS read-only
	STATUS current
	DESCRIPTION "Alarm equipment id."
	::= { systemAlarmTrapEntry 7 }	

systemAlarmEquipTypeId OBJECT-TYPE
	SYNTAX Integer32
	MAX-ACCESS read-only
	STATUS current
	DESCRIPTION "Alarm equipment type id."
	::= { systemAlarmTrapEntry 8 }
	
	
------------------------------------------------------------
-- System Alarm Trap { 13400.3.255 }
------------------------------------------------------------

systemAlarmTrap OBJECT IDENTIFIER ::= { dcs 255 }

systemAlarmTrapDefine NOTIFICATION-TYPE
	OBJECTS {
		systemAlarmIndex,
		systemAlarmTime,
		systemAlarmStatusChange,
		systemAlarmSeverity,
		systemAlarmDescription,
		systemAlarmId,
		systemAlarmEquipId,
		systemAlarmEquipTypeId }
	STATUS current
	DESCRIPTION "
		An alarm trap is sent when an alarm occurs (activated) or
		returns to normal state (deactivated). Alarm traps are logged
		in alarmTrapTable. Variables in this trap:
		* systemAlarmIndex - The unique sequence number of this alarm trap.
		* systemAlarmTime - Date and time when event occured (local time).
		* systemAlarmStatusChange - (0) activated or (1) deactivated.
		* systemAlarmSeverity - The severity of the alarm..
		* systemAlarmId - Alarm id.
		* systemAlarmEquipId - Alarm equipment id.
		* systemAlarmEquipTypeId - Alarm equipment type id."
	::= { systemAlarmTrap 1 }
	
	
------------------------------------------------------------
-- End of MIB definitions
------------------------------------------------------------
END
